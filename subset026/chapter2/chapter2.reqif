# Subset026

# Specification: Specification Document
- Description: Subset026

## 2
System Requirements Specification Chapter 2
Basic System Description
- implement: false
- kind: Heading
- atomic: true
- Legal Obligation: unknown
- WordTraceId: 16

### 2.1
Modification History
- implement: true
- kind: ordinary
- atomic: false
- Legal Obligation: not applicable
- WordTraceId: 146

### 2.1[2]
- implement: false
- kind: Placeholder
- atomic: false
- Legal Obligation: not applicable
- WordTraceId: 167

#### 2.1[2].[t]*
| Issue Number Date | Section Number | Modification / Description | Author |
| --- | --- | --- | --- |
| 0.0.1 19 july 1999 | All | First class 1 draft using new templates and including contributions from WPs | PZ |
| 0.1.0 26 july 1999 | System architecture figure § 2.3.1.2 | Updating and introduction of Radio infill Reference to future class 1 deleted | PZ |
| 1.0.0 29 July 1999 | Document version, editorial changes, updating the architecture figure. | Finalisation in Stuttgart 990729 | HE |
| 1.2.0 990730 | Version number | Release version | HE |
| 1.2.1 991209 | All | Draft for 2 nd release | SAB |
| 1.3.0 9912016 | All | Review comments added | SAB |
| 2.0.0 991222 | Minor editing | Finalisation | SAB |
| 2.0.1 | All | Corrections after review | SAB |
| 2.1.0 | Minor editing | UNISIG release | SAB |
| 2.2.0 | Version number | UNISIG release | SAB |
| 2.2.2 1.2.2002 | Version number | Final edition | Ch. Frerichs |
| 2.3.0 24/02/06 | Version number No change since 2.2.2 | Release version | HK |
| 2.3.2 17/03/08 | Including CRs that are in state “Analysis completed” according to ERA CCM | Working version | AH |
| 3.0.0 23/12/08 | Version number No change since 2.3.2 | Release version | AH |
| 3.0.1 22/12/09 |  | Including the results of the editorial review of the SRS 3.0.0 and the other error CR’s that are in state “Analysis completed” according to ERA CCM | AH |
| 3.1.0 22/02/10 |  | Release version | AH |
| 3.1.1 08/11/10 |  | Including all CR’s that are in state “Analysis completed” according to ERA CCM | AH |
| 3.2.0 22/12/10 | No change | Release version | AH |
| 3.2.1 13/12/11 |  | Including all CR’s that are in state “Analysis completed” according to ERA CCM | AH |
| 3.3.0 07/03/12 |  | Baseline 3 release version | AH |
- implement: false
- kind: Table
- atomic: false
- Legal Obligation: not applicable
- WordTraceId: 1713

### 2.2
Table of Contents
- implement: true
- kind: ordinary
- atomic: false
- Legal Obligation: not applicable
- WordTraceId: 1713

### 2.3
Introduction
- implement: false
- kind: Heading
- atomic: false
- Legal Obligation: not applicable
- WordTraceId: 2828

#### 2.3.1
Scope and purpose
- implement: false
- kind: Heading
- atomic: false
- Legal Obligation: not applicable
- WordTraceId: 2841

##### 2.3.1.1
The present chapter gives the basic description of the
ERTMS/ETCS system proposed to achieve technical interoperability.
- implement: true
- kind: ordinary
- atomic: true
- Legal Obligation: unknown
- WordTraceId: 2859

### 2.4
System structure
- implement: false
- kind: Heading
- atomic: false
- Legal Obligation: not applicable
- WordTraceId: 2981

#### 2.4.1
PLACEHOLDER REQUIREMENT - DO NOT TRACE
- implement: false
- kind: Placeholder
- atomic: false
- Legal Obligation: not applicable
- WordTraceId: 2998

##### 2.4.1.1
Due to the nature of the required functions, the
ERTMS/ETCS system
will have to be partly on the trackside and partly on board the trains.
- implementerEnhanced: Due to the nature of the required functions, the ERTMS/ETCS system will have to be partly on the
  trackside
  [EXTERNAL]
  and partly on board the trains.
- implement: true
- kind: ordinary
- atomic: true
- Legal Obligation: unknown
- WordTraceId: 2998

##### 2.4.1.2
This defines two sub-systems, the on-board sub-system and the trackside sub-system.
- implementerEnhanced: This defines two sub-systems, the on-board sub-system and the
  trackside
  [EXTERNAL]
  sub-system.
- implement: false
- kind: Definition
- atomic: true
- Legal Obligation: unknown
- WordTraceId: 3138

##### 2.4.1.3
The environment of ERTMS/ETCS system is composed of:
- implement: false
- kind: Heading
- atomic: true
- Legal Obligation: unknown
- WordTraceId: 3222

###### 2.4.1.3.a
the train, which will then be considered in the train interface specification;
- ListNumberText: a)
- implement: true
- kind: ordinary
- atomic: true
- Legal Obligation: unknown
- WordTraceId: 3275

###### 2.4.1.3.b
the driver, which will then be considered via the driver interface specification;
- implementerEnhanced: the
  driver
  [EXTERNAL]
  , which will then be considered via the
  driver
  [EXTERNAL]
  interface specification;
- ListNumberText: b)
- implement: true
- kind: ordinary
- atomic: true
- Legal Obligation: unknown
- WordTraceId: 3354

###### 2.4.1.3.c
other onboard interfaces (see architecture drawing in 2.5.3),
- ListNumberText: c)
- implement: true
- kind: ordinary
- atomic: true
- Legal Obligation: unknown
- WordTraceId: 3436
- CrossRefLink -> 2.5.3

###### 2.4.1.3.d
external trackside systems (interlockings, control centres, etc.), for which no interoperability requirement will be established.
- implementerEnhanced: external
  [EXTERNAL]
  trackside
  [EXTERNAL]
  systems (interlockings, control centres,
  etc.
  [WEAK]
  ), for which no interoperability requirement will be established.
- ListNumberText: d)
- implement: true
- kind: ordinary
- atomic: true
- Legal Obligation: unknown
- WordTraceId: 3498

### 2.5
Sub-systems
- implement: false
- kind: Heading
- atomic: false
- Legal Obligation: not applicable
- WordTraceId: 3629

#### 2.5.1
Trackside subsystem
- implementerEnhanced: Trackside
  [EXTERNAL]
  subsystem
- implement: false
- kind: Heading
- atomic: false
- Legal Obligation: not applicable
- WordTraceId: 3641

##### 2.5.1.1
Depending of the application level (see further sections), the trackside sub-system can be composed of:
- implementerEnhanced: Depending of the application level (see further sections), the
  trackside
  [EXTERNAL]
  sub-system can be composed of:
- implement: false
- kind: Heading
- atomic: true
- Legal Obligation: unknown
- WordTraceId: 3661

###### 2.5.1.1.a
balise
- implementerEnhanced: balise
  [EXTERNAL]
- ListNumberText: a)
- implement: true
- kind: ordinary
- atomic: true
- Legal Obligation: unknown
- WordTraceId: 3765

###### 2.5.1.1.b
lineside electronic unit
- implementerEnhanced: lineside electronic unit
  [EXTERNAL]
- ListNumberText: b)
- implement: true
- kind: ordinary
- atomic: true
- Legal Obligation: unknown
- WordTraceId: 3772

###### 2.5.1.1.c
the radio communication network (GSM-R)
- ListNumberText: c)
- implement: true
- kind: ordinary
- atomic: true
- Legal Obligation: unknown
- WordTraceId: 3797

###### 2.5.1.1.d
the Radio Block Centre (RBC)
- implementerEnhanced: the
  Radio Block Centre
  [EXTERNAL]
  (
  RBC
  [EXTERNAL]
  )
- ListNumberText: d)
- implement: true
- kind: ordinary
- atomic: true
- Legal Obligation: unknown
- WordTraceId: 3837

###### 2.5.1.1.e
Euroloop
- implementerEnhanced: Euroloop
  [EXTERNAL]
- ListNumberText: e)
- implement: true
- kind: ordinary
- atomic: true
- Legal Obligation: unknown
- WordTraceId: 3866

###### 2.5.1.1.f
Radio infill unit
- implementerEnhanced: Radio infill unit
  [EXTERNAL]
- ListNumberText: f)
- implement: true
- kind: ordinary
- atomic: true
- Legal Obligation: unknown
- WordTraceId: 3875

###### 2.5.1.1.g
Key Management Centre (KMC)
- ListNumberText: g)
- implement: true
- kind: ordinary
- atomic: true
- Legal Obligation: unknown
- WordTraceId: 3893

##### 2.5.1.2
Balise
- implementerEnhanced: Balise
  [EXTERNAL]
- implement: false
- kind: Heading
- atomic: false
- Legal Obligation: not applicable
- WordTraceId: 3921

###### 2.5.1.2.1
The balise is a transmission device that can send telegrams to the on-board sub-system.
- implementerEnhanced: The
  balise
  [EXTERNAL]
  is a transmission device that can send telegrams to the on-board sub-system.
- implement: true
- kind: ordinary
- atomic: true
- Legal Obligation: unknown
- WordTraceId: 3928

###### 2.5.1.2.2
The balise is based on the existing Eurobalise specifications. These documents are included in the frame of the ERTMS/ETCS specifications.
- implementerEnhanced: The
  balise
  [EXTERNAL]
  is based on the existing
  Eurobalise
  [EXTERNAL]
  specifications. These documents are included in the frame of the ERTMS/ETCS specifications.
- implement: true
- kind: ordinary
- atomic: false
- Legal Obligation: unknown
- WordTraceId: 4016

###### 2.5.1.2.3
The balises provides the up-link, i. e. the possibility to send messages from trackside to the on-board sub-system.
- implementerEnhanced: The
  balises
  [EXTERNAL]
  provides the up-link, i. e. the possibility to send messages from
  trackside
  [EXTERNAL]
  to the on-board sub-system.
- implement: true
- kind: ordinary
- atomic: true
- Legal Obligation: unknown
- WordTraceId: 4155

###### 2.5.1.2.4
The balises can provide fixed messages or, when connected to a lineside electronic unit, messages that can be changed.
- implementerEnhanced: The
  balises
  [EXTERNAL]
  can provide fixed messages or,
  when
  [CONDITION]
  connected to a
  lineside electronic unit
  [EXTERNAL]
  , messages that can be changed.
- implement: true
- kind: ordinary
- atomic: true
- Legal Obligation: unknown
- WordTraceId: 4271

###### 2.5.1.2.5
The balises will be organised in groups, each balise transmitting a telegram and the combination of all telegrams defining the message sent by the balise group.
- implementerEnhanced: The
  balises
  [EXTERNAL]
  will be organised in groups, each
  balise
  [EXTERNAL]
  transmitting a telegram and the combination of all telegrams defining the message sent by the
  balise group
  [EXTERNAL]
  .
- implement: true
- kind: ordinary
- atomic: true
- Legal Obligation: unknown
- WordTraceId: 4391

##### 2.5.1.3
Lineside electronic unit
- implementerEnhanced: Lineside electronic unit
  [EXTERNAL]
- implement: false
- kind: Heading
- atomic: false
- Legal Obligation: not applicable
- WordTraceId: 4552

###### 2.5.1.3.1
The lineside electronic units are electronic devices, that generate telegrams to be sent by balises, on basis of information received from external trackside systems.
- implementerEnhanced: The lineside electronic units are electronic devices, that generate telegrams to be sent by
  balises
  [EXTERNAL]
  , on basis of information received from
  external
  [EXTERNAL]
  trackside
  [EXTERNAL]
  systems.
- implement: true
- kind: ordinary
- atomic: true
- Legal Obligation: unknown
- WordTraceId: 4577

##### 2.5.1.4
Trackside radio communication network (GSM-R)
- implementerEnhanced: Trackside
  [EXTERNAL]
  radio communication network (GSM-R)
- implement: false
- kind: Heading
- atomic: false
- Legal Obligation: not applicable
- WordTraceId: 4744

###### 2.5.1.4.1
The GSM-R radio communication network is used for the bi-directional exchange of messages between on-board sub-systems and RBC or radio infill units.
- implementerEnhanced: The GSM-R radio communication network is used for the bi-directional exchange of messages between on-board sub-systems and
  RBC
  [EXTERNAL]
  or radio infill units.
- implement: true
- kind: ordinary
- atomic: true
- Legal Obligation: unknown
- WordTraceId: 4790

###### 2.5.1.4.2
Intentionally deleted
- implement: false
- kind: Placeholder
- atomic: false
- Legal Obligation: not applicable
- WordTraceId: 4941

##### 2.5.1.5
RBC
- implementerEnhanced: RBC
  [EXTERNAL]
- implement: false
- kind: Heading
- atomic: false
- Legal Obligation: not applicable
- WordTraceId: 4963

###### 2.5.1.5.1
The RBC is a computer-based system that elaborates messages to be sent to the train on basis of information received from external trackside systems and on basis of information exchanged with the on-board sub-systems.
- implementerEnhanced: The
  RBC
  [EXTERNAL]
  is a computer-based system that elaborates messages to be sent to the train on basis of information received from
  external
  [EXTERNAL]
  trackside
  [EXTERNAL]
  systems and on basis of information exchanged with the on-board sub-systems.
- implement: true
- kind: ordinary
- atomic: true
- Legal Obligation: unknown
- WordTraceId: 4967

###### 2.5.1.5.2
The main objective of these messages is to provide movement authorities to allow the safe movement of trains on the Railway infrastructure area under the responsibility of the RBC.
- implementerEnhanced: The main objective of these messages is to provide movement authorities to allow the safe movement of trains on the Railway infrastructure area under the responsibility of the
  RBC
  [EXTERNAL]
  .
- implement: true
- kind: ordinary
- atomic: true
- Legal Obligation: unknown
- WordTraceId: 5186

###### 2.5.1.5.3
The interoperability requirements for the RBC are mainly related to the data exchange between the RBC and the on-board sub-system.
- implementerEnhanced: The interoperability requirements for the
  RBC
  [EXTERNAL]
  are mainly related to the data exchange between the
  RBC
  [EXTERNAL]
  and the on-board sub-system.
- implement: true
- kind: ordinary
- atomic: true
- Legal Obligation: unknown
- WordTraceId: 5367

##### 2.5.1.6
Euroloop
- implementerEnhanced: Euroloop
  [EXTERNAL]
- implement: false
- kind: Heading
- atomic: false
- Legal Obligation: not applicable
- WordTraceId: 5498

###### 2.5.1.6.1
The Euroloop subsystem operates on Level 1 lines, providing signalling information in advance as regard to the next main signal in the train running direction.
- implementerEnhanced: The
  Euroloop
  [EXTERNAL]
  subsystem operates on Level 1 lines, providing signalling information in advance as regard to the next main signal in the train running direction.
- implement: true
- kind: ordinary
- atomic: true
- Legal Obligation: unknown
- WordTraceId: 5507

###### 2.5.1.6.2
The Euroloop subsystem is composed of an on-board functionality and by one or more trackside parts.
- implementerEnhanced: The
  Euroloop
  [EXTERNAL]
  subsystem is composed of an on-board functionality and by one or more
  trackside
  [EXTERNAL]
  parts.
- implement: true
- kind: ordinary
- atomic: true
- Legal Obligation: unknown
- WordTraceId: 5667

##### 2.5.1.7
Radio infill Unit
- implementerEnhanced: Radio infill Unit
  [EXTERNAL]
- implement: false
- kind: Heading
- atomic: false
- Legal Obligation: not applicable
- WordTraceId: 5768

###### 2.5.1.7.1
The RADIO INFILL subsystem operates on Level 1 lines, providing signalling information in advance as regard to the next main signal in the train running direction.
- implement: true
- kind: ordinary
- atomic: true
- Legal Obligation: unknown
- WordTraceId: 5786

###### 2.5.1.7.2
The RADIO INFILL subsystem is composed of an on-board functionality and by one or more trackside parts (named RADIO INFILL Unit).
- implementerEnhanced: The RADIO INFILL subsystem is composed of an on-board functionality and by one or more
  trackside
  [EXTERNAL]
  parts (named
  RADIO INFILL Unit
  [EXTERNAL]
  ).
- implement: true
- kind: ordinary
- atomic: true
- Legal Obligation: unknown
- WordTraceId: 5950

##### 2.5.1.8
KMC
- implement: false
- kind: Heading
- atomic: false
- Legal Obligation: not applicable
- WordTraceId: 6081

###### 2.5.1.8.1
The role of the KMC is to manage the cryptographic keys, which are used to secure the EURORADIO communications between the ERTMS/ETCS entities (ERTMS/ETCS on-board equipments, RBCs and RIUs).
- implementerEnhanced: The role of the KMC
  is to manage the cryptographic keys, which are used to secure the EURORADIO communications between the ERTMS/ETCS entities (
  ERTMS/ETCS on-board
  [SELF]
  equipments, RBCs and RIUs).
- implement: true
- kind: ordinary
- atomic: true
- Legal Obligation: unknown
- WordTraceId: 6085

#### 2.5.2
On-board sub-system
- implement: false
- kind: Heading
- atomic: false
- Legal Obligation: not applicable
- WordTraceId: 6277

##### 2.5.2.1
Depending of the application level (see further sections), the on-board sub-system can be composed of:
- implement: false
- kind: Heading
- atomic: true
- Legal Obligation: unknown
- WordTraceId: 6297

###### 2.5.2.1.a
the ERTMS/ETCS on-board equipment;
- implementerEnhanced: the
  ERTMS/ETCS
  on-board equipment
  [SELF]
  ;
- ListNumberText: a)
- implement: true
- kind: ordinary
- atomic: true
- Legal Obligation: unknown
- WordTraceId: 6400

###### 2.5.2.1.b
the on-board part of the GSM-R radio system;
- ListNumberText: b)
- implement: true
- kind: ordinary
- atomic: true
- Legal Obligation: unknown
- WordTraceId: 6435

##### 2.5.2.2
ERTMS/ETCS on-board equipment
- implementerEnhanced: ERTMS/ETCS on-board equipment
  [SELF]
- implement: false
- kind: Heading
- atomic: false
- Legal Obligation: not applicable
- WordTraceId: 6481

###### 2.5.2.2.1
The ERTMS/ETCS on-board equipment is a computer-based system that supervises the movement of the train to which it belongs, on basis of information exchanged with the trackside sub-system.
- implementerEnhanced: The
  ERTMS/ETCS on-board equipment
  [SELF]
  is a computer-based system that supervises the movement of the train to which it belongs, on basis of information exchanged with the
  trackside
  [EXTERNAL]
  sub-system.
- implement: true
- kind: ordinary
- atomic: true
- Legal Obligation: unknown
- WordTraceId: 6511

###### 2.5.2.2.2
The interoperability requirements for the ERTMS/ETCS on-board equipment are related to the functionality and the data exchange between the trackside sub-systems and the on-board sub-system and to the functional data exchange between the on-board sub-system and:
- implementerEnhanced: The interoperability requirements for the
  ERTMS/ETCS on-board equipment
  [SELF]
  are related to the functionality and the data exchange between the
  trackside
  [EXTERNAL]
  sub-systems and the on-board sub-system and to the functional data exchange between the on-board sub-system and:
- implement: false
- kind: Heading
- atomic: true
- Legal Obligation: unknown
- WordTraceId: 6701

###### 2.5.2.2.2.a
the driver;
- implementerEnhanced: the
  driver
  [EXTERNAL]
  ;
- ListNumberText: a)
- implement: true
- kind: ordinary
- atomic: true
- Legal Obligation: unknown
- WordTraceId: 6963

###### 2.5.2.2.2.b
the train;
- ListNumberText: b)
- implement: true
- kind: ordinary
- atomic: true
- Legal Obligation: unknown
- WordTraceId: 6975

###### 2.5.2.2.2.c
the onboard part of the existing national train control system(s).
- ListNumberText: c)
- implement: true
- kind: ordinary
- atomic: true
- Legal Obligation: unknown
- WordTraceId: 6986

##### 2.5.2.3
Onboard radio communication system (GSM-R)
- implement: false
- kind: Heading
- atomic: false
- Legal Obligation: not applicable
- WordTraceId: 7053

###### 2.5.2.3.1
The GSM-R on-board radio system is used for the bi-directional exchange of messages between on-board sub-system and RBC or radio infill unit.
- implementerEnhanced: The GSM-R on-board radio system is used for the bi-directional exchange of messages between on-board sub-system and
  RBC
  [EXTERNAL]
  or
  radio infill unit
  [EXTERNAL]
  .
- implement: true
- kind: ordinary
- atomic: true
- Legal Obligation: unknown
- WordTraceId: 7096

###### 2.5.2.3.2
Intentionally deleted.
- implement: false
- kind: Placeholder
- atomic: false
- Legal Obligation: not applicable
- WordTraceId: 7239

#### 2.5.3
ERTMS/ETCS reference architecture
- implement: true
- kind: ordinary
- atomic: false
- Legal Obligation: not applicable
- WordTraceId: 7262

#### 2.5.3[2]
- implement: false
- kind: Placeholder
- atomic: false
- Legal Obligation: not applicable
- WordTraceId: 7297

##### 2.5.3[2].[f]1
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- implement: false
- kind: Figure
- atomic: false
- Legal Obligation: not applicable
- WordTraceId: 7327

###### 2.5.3[2].[f]1.C
Figure {Figure 1}: ERTMS/ETCS system and its interfaces
- implementerEnhanced: Figure 1: ERTMS/ETCS system and its interfaces
- implement: false
- kind: Figure
- atomic: true
- Legal Obligation: unknown
- WordTraceId: 7327

##### 2.5.3[2].1
Note: the entities inside the ERTMS/ETCS on-board equipment box are shown only to highlight the scope of the interfaces that are specified in the TSI CCS annex A.
- implementerEnhanced: Note: the entities inside the
  ERTMS/ETCS on-board equipment
  [SELF]
  box are shown only to highlight the scope of the interfaces that are specified in the TSI CCS annex A.
- ListNumberText: 2.5.3.1
- implement: false
- kind: Note
- atomic: false
- Legal Obligation: not applicable
- WordTraceId: 7399

### 2.6
Levels and transitions
- implement: false
- kind: Heading
- atomic: false
- Legal Obligation: not applicable
- WordTraceId: 7563

#### 2.6.1
Introduction
- implement: false
- kind: Heading
- atomic: false
- Legal Obligation: not applicable
- WordTraceId: 7586

##### 2.6.1.1
The different ERTMS/ETCS application levels (short: levels) are a way to express the possible operating relationships between track and train. Level definitions are related to the trackside equipment used, to the way trackside information reaches the on-board units and to which functions are processed in the trackside and in the on-board equipment respectively.
- implementerEnhanced: The different ERTMS/ETCS application levels (short: levels) are a way to express the possible operating relationships between track and train. Level definitions are related to the
  trackside
  [EXTERNAL]
  equipment used, to the way
  trackside
  [EXTERNAL]
  information reaches the on-board units and to which functions are processed in the
  trackside
  [EXTERNAL]
  and in the
  on-board equipment
  [SELF]
  respectively.
- implement: true
- kind: ordinary
- atomic: false
- Legal Obligation: unknown
- WordTraceId: 7599

##### 2.6.1.2
Different levels have been defined to allow each individual railway administration to select the appropriate ERTMS/ETCS application trackside, according to their strategies, to their trackside infrastructure and to the required performance. Furthermore, the different application levels permit the interfacing of individual signalling systems and train control systems to ERTMS/ETCS.
- implementerEnhanced: Different levels have been defined to allow each individual railway administration to select the appropriate ERTMS/ETCS application
  trackside
  [EXTERNAL]
  , according to their strategies, to their
  trackside
  [EXTERNAL]
  infrastructure and to the required performance. Furthermore, the different application levels permit the interfacing of individual signalling systems and train control systems to ERTMS/ETCS.
- implement: true
- kind: ordinary
- atomic: false
- Legal Obligation: unknown
- WordTraceId: 7964

##### 2.6.1.3
For the purpose of a consistent specification a level 0 has been defined. This level is used for operation on non-equipped (unfitted) lines or on lines equipped with train control system(s) but operation under their supervision is currently not possible.
- implement: true
- kind: ordinary
- atomic: false
- Legal Obligation: unknown
- WordTraceId: 8348

#### 2.6.2
Definitions
- implement: false
- kind: Heading
- atomic: false
- Legal Obligation: not applicable
- WordTraceId: 8604

##### 2.6.2.1
A train equipped with ERTMS/ETCS on-board equipment always co-operates with the ERTMS/ETCS trackside equipment in a defined ERTMS/ETCS level.
- implementerEnhanced: A train equipped with
  ERTMS/ETCS on-board equipment
  [SELF]
  always co-operates with the ERTMS/ETCS
  trackside
  [EXTERNAL]
  equipment in a defined ERTMS/ETCS level.
- implement: true
- kind: ordinary
- atomic: true
- Legal Obligation: unknown
- WordTraceId: 8616

##### 2.6.2.2
All transitions between levels are performed according to well-specified rules.
- implement: true
- kind: ordinary
- atomic: true
- Legal Obligation: unknown
- WordTraceId: 8759

##### 2.6.2.3
ERTMS/ETCS can be configured to operate in one of the following application levels:
- implement: false
- kind: Heading
- atomic: true
- Legal Obligation: unknown
- WordTraceId: 8840

###### 2.6.2.3.*[1]
ERTMS/ETCS Level 0 (train equipped with ERTMS/ETCS operating on a line not equipped with any train control system (ERTMS/ETCS or national system) or on a line equipped with ERTMS/ETCS and/or national system(s) but operation under their supervision is currently not possible)
- implementerEnhanced: ERTMS/ETCS Level 0 (train equipped with ERTMS/ETCS operating on a line not equipped with any train control system (ERTMS/ETCS or
  national system
  [EXTERNAL]
  ) or on a line equipped with ERTMS/ETCS and/or national system(s) but operation under their supervision is currently not possible)
- ListNumberText: ·
- implement: true
- kind: ordinary
- atomic: true
- Legal Obligation: unknown
- WordTraceId: 8925

###### 2.6.2.3.*[2]
ERTMS/ETCS Level NTC (train equipped with ERTMS/ETCS operating on a line equipped with a national system)
- implementerEnhanced: ERTMS/ETCS Level NTC
  (train equipped with ERTMS/ETCS operating on a line equipped with a
  national system
  [EXTERNAL]
  )
- ListNumberText: ·
- implement: true
- kind: ordinary
- atomic: true
- Legal Obligation: unknown
- WordTraceId: 9200

###### 2.6.2.3.*[3]
ERTMS/ETCS Application Level 1 with or without infill transmission (train equipped with ERTMS/ETCS operating on a line equipped with Eurobalises and optionally Euroloop or Radio infill)
- implementerEnhanced: ERTMS/ETCS Application Level 1 with or without infill transmission (train equipped with ERTMS/ETCS operating on a line equipped with
  Eurobalises
  [EXTERNAL]
  and optionally
  Euroloop
  [EXTERNAL]
  or Radio infill)
- ListNumberText: ·
- implement: true
- kind: ordinary
- atomic: true
- Legal Obligation: unknown
- WordTraceId: 9306

###### 2.6.2.3.*[4]
ERTMS/ETCS Application Level 2 (train equipped with ERTMS/ETCS operating on a line controlled by a Radio Block Centre and equipped with Eurobalises and Euroradio) with train position and train integrity proving performed by the trackside
- implementerEnhanced: ERTMS/ETCS Application Level 2 (train equipped with ERTMS/ETCS operating on a line controlled by a
  Radio Block Centre
  [EXTERNAL]
  and equipped with
  Eurobalises
  [EXTERNAL]
  and Euroradio) with train position and train integrity proving performed by the
  trackside
  [EXTERNAL]
- ListNumberText: ·
- implement: true
- kind: ordinary
- atomic: true
- Legal Obligation: unknown
- WordTraceId: 9492

###### 2.6.2.3.*[5]
ERTMS/ETCS Application Level 3 (similar to level 2 but with train position and train integrity supervision based on information received from the train)
- ListNumberText: ·
- implement: true
- kind: ordinary
- atomic: true
- Legal Obligation: unknown
- WordTraceId: 9730

##### 2.6.2.4
It is possible to superimpose several application levels in parallel on the same track, for example to run trains without train integrity device in level 2 and in parallel trains equipped with train integrity device in level 3. Other examples might be a station which is shared by trains arriving over level 1 and level 2 lines (junctions) or parallel operation of a national system with ERTMS/ETCS. Mixed levels are supported.
- implementerEnhanced: It is possible to superimpose several application levels in parallel on the same track,
  for example
  [WEAK]
  to run trains without train integrity device in level 2 and in parallel trains equipped with train integrity device in level 3. Other examples might be a station which is shared by trains arriving over level 1 and level 2 lines (junctions) or parallel operation of a
  national system
  [EXTERNAL]
  with ERTMS/ETCS. Mixed levels are supported.
- implement: true
- kind: ordinary
- atomic: false
- Legal Obligation: unknown
- WordTraceId: 9884

##### 2.6.2.5
Levels 1, 2 and 3 are downwards compatible. This means that:
- implement: true
- kind: ordinary
- atomic: false
- Legal Obligation: unknown
- WordTraceId: 10312

###### 2.6.2.5.*[1]
a level 3 equipped train is also able to operate in level 0, level 1 and level 2
- ListNumberText: ·
- implement: true
- kind: ordinary
- atomic: true
- Legal Obligation: unknown
- WordTraceId: 10373

###### 2.6.2.5.*[2]
a level 2 equipped train is also able to operate in level 0 and level 1
- ListNumberText: ·
- implement: true
- kind: ordinary
- atomic: true
- Legal Obligation: unknown
- WordTraceId: 10454

###### 2.6.2.5.*[3]
a level 1 equipped train is also able to operate in level 0
- ListNumberText: ·
- implement: true
- kind: ordinary
- atomic: true
- Legal Obligation: unknown
- WordTraceId: 10526

##### 2.6.2.6
Note: Operation under level NTC is not part of the downward compatibility chain.
- implement: false
- kind: Note
- atomic: false
- Legal Obligation: not applicable
- WordTraceId: 10587

##### 2.6.2.7
It is possible to transmit information not intended for ERTMS/ETCS but for other systems over the ERTMS/ETCS transmission channels. This information is not used by ERTMS/ETCS.
- implement: true
- kind: ordinary
- atomic: false
- Legal Obligation: unknown
- WordTraceId: 10668

#### 2.6.3
ERTMS/ETCS Application Level 0
- implement: false
- kind: Heading
- atomic: false
- Legal Obligation: not applicable
- WordTraceId: 10845

##### 2.6.3.1
General description
- implement: false
- kind: Heading
- atomic: false
- Legal Obligation: not applicable
- WordTraceId: 10876

###### 2.6.3.1.1
Level 0 covers operation of ETCS equipped trains on lines not equipped with ETCS or national systems or on lines where trackside ERTMS/ETCS infrastructure and/or national systems may exist but operation under their supervision is currently not possible (e.g. commissioning or on-board/trackside failed components).
- implementerEnhanced: Level 0 covers operation of ETCS equipped trains on lines not equipped with ETCS or national systems or on lines where
  trackside
  [EXTERNAL]
  ERTMS/ETCS infrastructure and/or national systems may exist but operation under their supervision is currently not possible (
  e.g.
  [WEAK]
  commissioning or on-board/
  trackside
  [EXTERNAL]
  failed components).
- implement: true
- kind: ordinary
- atomic: true
- Legal Obligation: optional
- WordTraceId: 10896

###### 2.6.3.1.2
In Level 0 it is authorized to operate trains without any train control system and therefore line side optical signals or other means of signalling are used to give movement authorities to the driver.
- implementerEnhanced: In Level 0 it is authorized to operate trains without any train control system and therefore line side optical signals or other means of signalling are used to give movement authorities to the
  driver
  [EXTERNAL]
  .
- implement: true
- kind: ordinary
- atomic: true
- Legal Obligation: unknown
- WordTraceId: 11212

###### 2.6.3.1.3
ERTMS/ETCS on-board equipment provides no supervision except of the maximum design speed of a train and maximum speed permitted in unfitted areas.
- implementerEnhanced: ERTMS/ETCS on-board equipment
  [SELF]
  provides no supervision except of the maximum design speed of a train and maximum speed permitted in unfitted areas.
- implement: true
- kind: ordinary
- atomic: true
- Legal Obligation: unknown
- WordTraceId: 11414

###### 2.6.3.1.4
Train detection and train integrity supervision are performed by the trackside equipment of the underlying signalling system (interlocking, track circuits etc.) and are outside the scope of ERTMS/ETCS.
- implementerEnhanced: Train detection and train integrity supervision are performed by the
  trackside
  [EXTERNAL]
  equipment of the underlying signalling system (interlocking, track circuits
  etc.
  [WEAK]
  ) and are outside the scope of ERTMS/ETCS.
- implement: true
- kind: ordinary
- atomic: true
- Legal Obligation: unknown
- WordTraceId: 11562

###### 2.6.3.1.5
Level 0 uses no track-train transmission except Eurobalises to announce/command level transitions. Eurobalises therefore still have to be read. No balise data except certain special commands are interpreted.
- implementerEnhanced: Level 0 uses no track-train transmission except
  Eurobalises
  [EXTERNAL]
  to announce/command level transitions.
  Eurobalises
  [EXTERNAL]
  therefore still have to be read. No
  balise
  [EXTERNAL]
  data except certain special commands are interpreted.
- implement: true
- kind: ordinary
- atomic: false
- Legal Obligation: unknown
- WordTraceId: 11764

###### 2.6.3.1.6
No supervisory information is indicated on the DMI except the train speed. Train data has to be entered in order not to have to stop a train at a level transition to ERTMS/ETCS equipped area and to supervise maximum train speed.
- implement: true
- kind: ordinary
- atomic: false
- Legal Obligation: unknown
- WordTraceId: 11972

###### 2.6.3.1.6[2]
- implement: false
- kind: Placeholder
- atomic: false
- Legal Obligation: not applicable
- WordTraceId: 12201

###### 2.6.3.1.6[2].[f]2
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- implement: false
- kind: Figure
- atomic: false
- Legal Obligation: not applicable
- WordTraceId: 12203

###### 2.6.3.1.6[2].[f]2.C
Figure {Figure 2}: ERTMS/ETCS Application Level 0
- implementerEnhanced: Figure 2: ERTMS/ETCS Application Level 0
- PlainText: Figure 2: ERTMS/ETCS Application Level 0
- implement: false
- kind: Figure
- atomic: true
- Legal Obligation: unknown
- WordTraceId: 12203

##### 2.6.3.2
Summary of characteristics of Application Level 0
- implement: false
- kind: Heading
- atomic: false
- Legal Obligation: not applicable
- WordTraceId: 12269

###### 2.6.3.2.1
Trackside equipment:
- implementerEnhanced: Trackside
  [EXTERNAL]
  equipment:
- implement: false
- kind: Heading
- atomic: true
- Legal Obligation: unknown
- WordTraceId: 12319

###### 2.6.3.2.1.*[1]
No ERTMS/ETCS trackside equipment is used except for Eurobalises to announce level transitions and other specific commands.
- implementerEnhanced: No ERTMS/ETCS
  trackside
  [EXTERNAL]
  equipment is used except for
  Eurobalises
  [EXTERNAL]
  to announce level transitions and other specific commands.
- ListNumberText: ·
- implement: true
- kind: ordinary
- atomic: true
- Legal Obligation: unknown
- WordTraceId: 12341

###### 2.6.3.2.2
Main ERTMS/ETCS trackside functions:
- implementerEnhanced: Main
  ERTMS/ETCS
  trackside
  [EXTERNAL]
  functions:
- implement: false
- kind: Heading
- atomic: true
- Legal Obligation: unknown
- WordTraceId: 12465

###### 2.6.3.2.2.*[1]
None.
- ListNumberText: ·
- implement: true
- kind: ordinary
- atomic: true
- Legal Obligation: unknown
- WordTraceId: 12502

###### 2.6.3.2.3
On-board equipment:
- implementerEnhanced: On-board equipment
  [SELF]
  :
- implement: false
- kind: Heading
- atomic: true
- Legal Obligation: unknown
- WordTraceId: 12508

###### 2.6.3.2.3.*[1]
Onboard equipment with Eurobalise transmission.
- implementerEnhanced: Onboard equipment
  [SELF]
  with
  Eurobalise
  [EXTERNAL]
  transmission.
- ListNumberText: ·
- implement: true
- kind: ordinary
- atomic: true
- Legal Obligation: unknown
- WordTraceId: 12528

###### 2.6.3.2.4
Main ERTMS/ETCS on-board functions:
- implementerEnhanced: Main
  ERTMS/ETCS
  on-board
  [SELF]
  functions:
- implement: false
- kind: Heading
- atomic: true
- Legal Obligation: unknown
- WordTraceId: 12576

###### 2.6.3.2.4.*[1]
Supervision of maximum train speed.
- ListNumberText: ·
- implement: true
- kind: ordinary
- atomic: true
- Legal Obligation: unknown
- WordTraceId: 12612

###### 2.6.3.2.4.*[2]
Supervision of maximum speed permitted in an unfitted area.
- ListNumberText: ·
- implement: true
- kind: ordinary
- atomic: true
- Legal Obligation: unknown
- WordTraceId: 12648

###### 2.6.3.2.4.*[3]
Reading of Eurobalises to detect level transitions and certain special commands. All other messages are rejected.
- implementerEnhanced: Reading of
  Eurobalises
  [EXTERNAL]
  to detect level transitions and certain special commands. All other messages are rejected.
- ListNumberText: ·
- implement: true
- kind: ordinary
- atomic: false
- Legal Obligation: unknown
- WordTraceId: 12708

###### 2.6.3.2.4.*[4]
No cab signalling.
- ListNumberText: ·
- implement: true
- kind: ordinary
- atomic: true
- Legal Obligation: unknown
- WordTraceId: 12822

#### 2.6.4
ERTMS/ETCS Application Level NTC
- implement: false
- kind: Heading
- atomic: false
- Legal Obligation: not applicable
- WordTraceId: 12842

##### 2.6.4.1
General description
- implement: false
- kind: Heading
- atomic: false
- Legal Obligation: not applicable
- WordTraceId: 12875

###### 2.6.4.1.1
Level NTC is used to run ERTMS/ETCS equipped trains on lines equipped with national train control and speed supervision systems.
- implement: true
- kind: ordinary
- atomic: true
- Legal Obligation: unknown
- WordTraceId: 12895

###### 2.6.4.1.2
Train control information generated trackside by the national train control system is transmitted to the train via the communication channels of the underlying national system.
- implementerEnhanced: Train control information generated
  trackside
  [EXTERNAL]
  by the national train control system is transmitted to the train via the communication channels of the underlying
  national system
  [EXTERNAL]
  .
- implement: true
- kind: ordinary
- atomic: true
- Legal Obligation: unknown
- WordTraceId: 13025

###### 2.6.4.1.3
Note: Lineside optical signals might be necessary or not, depending on the performance and functionality of the underlying systems.
- implement: false
- kind: Note
- atomic: false
- Legal Obligation: not applicable
- WordTraceId: 13203

###### 2.6.4.1.4
Intentionally deleted.
- implement: false
- kind: Placeholder
- atomic: false
- Legal Obligation: not applicable
- WordTraceId: 13336

###### 2.6.4.1.5
The achievable level of supervision is similar to the one provided by the underlying national systems.
- implement: true
- kind: ordinary
- atomic: true
- Legal Obligation: unknown
- WordTraceId: 13360

###### 2.6.4.1.6
Train detection and train integrity supervision are performed by equipment external to ERTMS/ETCS.
- implementerEnhanced: Train detection and train integrity supervision are performed by equipment
  external
  [EXTERNAL]
  to ERTMS/ETCS.
- implement: true
- kind: ordinary
- atomic: true
- Legal Obligation: unknown
- WordTraceId: 13464

###### 2.6.4.1.7
Level NTC uses no ERTMS/ETCS track-train information except to announce/command level transitions and specific commands related to balise transmission. Eurobalises therefore still have to be read.
- implementerEnhanced: Level NTC
  uses no ERTMS/ETCS track-train information except to announce/command level transitions and specific commands related to
  balise
  [EXTERNAL]
  transmission.
  Eurobalises
  [EXTERNAL]
  therefore still have to be read.
- implement: true
- kind: ordinary
- atomic: false
- Legal Obligation: unknown
- WordTraceId: 13564

###### 2.6.4.1.8
The information displayed to the driver depends on the functionality of the underlying national system. The active national system is indicated to the driver as part of that information. Full train data has to be entered in order not to have to stop a train at a level transition position and to supervise maximum train speed.
- implementerEnhanced: The information displayed to the
  driver
  [EXTERNAL]
  depends on the functionality of the underlying
  national system
  [EXTERNAL]
  . The active
  national system
  [EXTERNAL]
  is indicated to the
  driver
  [EXTERNAL]
  as part of that information. Full train data has to be entered in order not to have to stop a train at a level transition position and to supervise maximum train speed.
- implement: true
- kind: ordinary
- atomic: false
- Legal Obligation: unknown
- WordTraceId: 13761

###### 2.6.4.1.9
A combination of national systems can be regarded as one NTC level.
- implement: true
- kind: ordinary
- atomic: true
- Legal Obligation: unknown
- WordTraceId: 14088

###### 2.6.4.1.10
Depending on the functionality and the configuration of the specific national system installed onboard, the ERTMS/ETCS Onboard system may need to be interfaced to it, in order to perform the transitions from/to the national system and/or in order to give access to ERTMS/ETCS Onboard resources (e.g. DMI). This can be achieved through a device called an STM (Specific Transmission Module) using a standardised interface.
- implementerEnhanced: Depending on the functionality and the configuration of the specific
  national system
  [EXTERNAL]
  installed onboard, the
  ERTMS/ETCS Onboard
  [SELF]
  system may need to be interfaced to it, in order to perform the transitions from/to the
  national system
  [EXTERNAL]
  and/or in order to give access to
  ERTMS/ETCS Onboard
  [SELF]
  resources (
  e.g.
  [WEAK]
  DMI). This can be achieved through a device called an STM (Specific Transmission Module) using a standardised interface.
- implement: true
- kind: ordinary
- atomic: false
- Legal Obligation: optional
- WordTraceId: 14156

###### 2.6.4.1.11
Intentionally deleted.
- implement: false
- kind: Placeholder
- atomic: false
- Legal Obligation: not applicable
- WordTraceId: 14577

###### 2.6.4.1.11[2]
- implement: false
- kind: Placeholder
- atomic: false
- Legal Obligation: not applicable
- WordTraceId: 14601

###### 2.6.4.1.11[2].[f]3
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- implement: false
- kind: Figure
- atomic: false
- Legal Obligation: not applicable
- WordTraceId: 14620

###### 2.6.4.1.11[2].[f]3.C
Figure {Figure 3}: ERTMS/ETCS Application Level NTC
- implementerEnhanced: Figure 3: ERTMS/ETCS Application Level NTC
- implement: false
- kind: Figure
- atomic: true
- Legal Obligation: unknown
- WordTraceId: 14620

##### 2.6.4.2
Summary of characteristics of Application Level NTC
- implement: false
- kind: Heading
- atomic: false
- Legal Obligation: not applicable
- WordTraceId: 14688

###### 2.6.4.2.1
Trackside equipment:
- implementerEnhanced: Trackside
  [EXTERNAL]
  equipment:
- implement: false
- kind: Heading
- atomic: true
- Legal Obligation: unknown
- WordTraceId: 14740

###### 2.6.4.2.1.*[1]
Level NTC uses the track-train transmission system from an underlying national system, which is not part of ERTMS/ETCS.
- implementerEnhanced: Level NTC
  uses the track-train transmission system from an underlying
  national system
  [EXTERNAL]
  , which is not part of ERTMS/ETCS.
- ListNumberText: ·
- implement: true
- kind: ordinary
- atomic: true
- Legal Obligation: unknown
- WordTraceId: 14762

###### 2.6.4.2.1.*[2]
For level transition purposes Eurobalises are used.
- implementerEnhanced: For level transition purposes
  Eurobalises
  [EXTERNAL]
  are used.
- ListNumberText: ·
- implement: true
- kind: ordinary
- atomic: true
- Legal Obligation: unknown
- WordTraceId: 14882

###### 2.6.4.2.2
Main ERTMS/ETCS trackside functions:
- implementerEnhanced: Main
  ERTMS/ETCS
  trackside
  [EXTERNAL]
  functions:
- implement: false
- kind: Heading
- atomic: true
- Legal Obligation: unknown
- WordTraceId: 14934

###### 2.6.4.2.2.*[1]
None.
- ListNumberText: ·
- implement: true
- kind: ordinary
- atomic: true
- Legal Obligation: unknown
- WordTraceId: 14971

###### 2.6.4.2.3
On-board equipment:
- implementerEnhanced: On-board equipment
  [SELF]
  :
- implement: false
- kind: Heading
- atomic: true
- Legal Obligation: unknown
- WordTraceId: 14977

###### 2.6.4.2.3.*[1]
Onboard equipment with Eurobalise transmission.
- implementerEnhanced: Onboard equipment
  [SELF]
  with
  Eurobalise
  [EXTERNAL]
  transmission.
- ListNumberText: ·
- implement: true
- kind: ordinary
- atomic: true
- Legal Obligation: unknown
- WordTraceId: 14998

###### 2.6.4.2.3.*[2]
Onboard part of the national system.
- implementerEnhanced: Onboard part of the
  national system
  [EXTERNAL]
  .
- ListNumberText: ·
- implement: true
- kind: ordinary
- atomic: true
- Legal Obligation: unknown
- WordTraceId: 15046

###### 2.6.4.2.4
Main ERTMS/ETCS on-board function:
- implementerEnhanced: Main
  ERTMS/ETCS
  on-board
  [SELF]
  function:
- implement: false
- kind: Heading
- atomic: true
- Legal Obligation: unknown
- WordTraceId: 15083

###### 2.6.4.2.4.*[1]
No train supervision, it is fully handed over to the national system.
- implementerEnhanced: No train supervision, it is fully handed over to the
  national system
  [EXTERNAL]
  .
- ListNumberText: ·
- implement: true
- kind: ordinary
- atomic: true
- Legal Obligation: unknown
- WordTraceId: 15118

###### 2.6.4.2.4.*[2]
Reading of Eurobalises to detect level transitions and certain special commands. All other messages are rejected.
- implementerEnhanced: Reading of
  Eurobalises
  [EXTERNAL]
  to detect level transitions and certain special commands. All other messages are rejected.
- ListNumberText: ·
- implement: true
- kind: ordinary
- atomic: false
- Legal Obligation: unknown
- WordTraceId: 15189

###### 2.6.4.2.4.*[3]
Management of the national system through STM, in case the ERTMS/ETCS on-board equipment is interfaced to the national system through an STM.
- implementerEnhanced: Management of the
  national system
  [EXTERNAL]
  through STM
  ,
  in case
  [CONDITION]
  the
  ERTMS/ETCS on-board equipment
  [SELF]
  is interfaced to the
  national system
  [EXTERNAL]
  through an STM.
- ListNumberText: ·
- implement: true
- kind: ordinary
- atomic: true
- Legal Obligation: unknown
- WordTraceId: 15303

###### 2.6.4.2.4.*[4]
No cab signalling.
- ListNumberText: ·
- implement: true
- kind: ordinary
- atomic: true
- Legal Obligation: unknown
- WordTraceId: 15445

#### 2.6.5
ERTMS/ETCS Application Level 1
- implement: false
- kind: Heading
- atomic: false
- Legal Obligation: not applicable
- WordTraceId: 15464

##### 2.6.5.1
General description
- implement: false
- kind: Heading
- atomic: false
- Legal Obligation: not applicable
- WordTraceId: 15495

###### 2.6.5.1.1
ERTMS/ETCS Level 1 is a spot transmission based train control system to be used as an overlay on an underlying signalling system.
- implement: true
- kind: ordinary
- atomic: true
- Legal Obligation: unknown
- WordTraceId: 15515

###### 2.6.5.1.2
Movement authorities are generated trackside and are transmitted to the train via Eurobalises.
- implementerEnhanced: Movement authorities are generated
  trackside
  [EXTERNAL]
  and are transmitted to the train via
  Eurobalises
  [EXTERNAL]
  .
- implement: true
- kind: ordinary
- atomic: true
- Legal Obligation: unknown
- WordTraceId: 15645

###### 2.6.5.1.3
ERTMS/ETCS Level 1 provides a continuous speed supervision system, which also protects against overrun of the authority.
- implement: true
- kind: ordinary
- atomic: true
- Legal Obligation: unknown
- WordTraceId: 15742

###### 2.6.5.1.4
Train detection and train integrity supervision are performed by the trackside equipment of the underlying signalling system (interlocking, track circuits etc.) and are outside the scope of ERTMS/ETCS.
- implementerEnhanced: Train detection and train integrity supervision are performed by the
  trackside
  [EXTERNAL]
  equipment of the underlying signalling system (interlocking, track circuits
  etc.
  [WEAK]
  ) and are outside the scope of ERTMS/ETCS.
- implement: true
- kind: ordinary
- atomic: true
- Legal Obligation: unknown
- WordTraceId: 15864

###### 2.6.5.1.5
Level 1 is based on Eurobalises as spot transmission devices.
- implementerEnhanced: Level 1 is based on
  Eurobalises
  [EXTERNAL]
  as spot transmission devices.
- implement: true
- kind: ordinary
- atomic: true
- Legal Obligation: unknown
- WordTraceId: 16066

###### 2.6.5.1.6
The trackside equipment does not know the train to which it sends information.
- implementerEnhanced: The
  trackside
  [EXTERNAL]
  equipment does not know the train to which it sends information.
- implement: true
- kind: ordinary
- atomic: true
- Legal Obligation: unknown
- WordTraceId: 16130

###### 2.6.5.1.7
If in level 1 a lineside signal clears, an approaching train can not receive this information until it passes the Eurobalise group at that signal. The driver therefore has to observe the lineside signal to know when to proceed. The train has then to be permitted to approach the stopping location below a maximum permitted release speed.
- implementerEnhanced: If
  [CONDITION]
  in level 1 a lineside signal clears, an approaching train can not receive this information
  until
  [TIME]
  it passes the
  Eurobalise
  [EXTERNAL]
  group at that signal. The
  driver
  [EXTERNAL]
  therefore has to observe the lineside signal to know
  when
  [CONDITION]
  to proceed. The train has then to be permitted to approach the stopping location
  below
  [WEAK]
  a maximum permitted release speed.
- implement: true
- kind: ordinary
- atomic: false
- Legal Obligation: unknown
- WordTraceId: 16209

###### 2.6.5.1.8
Additional Eurobalises can be placed between distant and main signals to transmit infill information, the train will receive new information before reaching the signal.
- implementerEnhanced: Additional
  Eurobalises
  [EXTERNAL]
  can be placed between distant and main signals to transmit infill information, the train will receive new information before reaching the signal.
- implement: true
- kind: ordinary
- atomic: true
- Legal Obligation: unknown
- WordTraceId: 16548

###### 2.6.5.1.9
Note: Lineside signals are required in level 1 applications, except if semi-continuous infill is provided.
- implementerEnhanced: Note: Lineside signals are required in level 1 applications, except
  if
  [CONDITION]
  semi-continuous infill is provided.
- implement: false
- kind: Note
- atomic: false
- Legal Obligation: not applicable
- WordTraceId: 16718

###### 2.6.5.1.10
Semi-continuous infill can be provided using Euroloop or radio infill. In this case, the on-board system will be able to show new information to the driver as soon as it is available and even at standstill.
- implementerEnhanced: Semi-continuous infill can be provided using
  Euroloop
  [EXTERNAL]
  or radio infill. In this case, the on-board system will be able to show new information to the
  driver
  [EXTERNAL]
  as soon as
  [WEAK]
  it is available and even at standstill.
- implement: true
- kind: ordinary
- atomic: false
- Legal Obligation: unknown
- WordTraceId: 16825

###### 2.6.5.1.11
Euroloop or radio infill can improve the safety of a level 1 system as they allow the operation without release speed.
- implementerEnhanced: Euroloop
  [EXTERNAL]
  or radio infill can improve the safety of a level 1 system as they allow the operation without release speed.
- implement: true
- kind: ordinary
- atomic: true
- Legal Obligation: unknown
- WordTraceId: 17033

###### 2.6.5.1.11[2]
- implement: false
- kind: Placeholder
- atomic: false
- Legal Obligation: not applicable
- WordTraceId: 17152

###### 2.6.5.1.11[2].[f]4
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- implement: false
- kind: Figure
- atomic: false
- Legal Obligation: not applicable
- WordTraceId: 17171

###### 2.6.5.1.11[2].[f]4.C
Figure {Figure 4}: ERTMS/ETCS Application Level 1 without infill function
- implementerEnhanced: Figure 4: ERTMS/ETCS Application Level 1 without infill function
- implement: false
- kind: Figure
- atomic: true
- Legal Obligation: unknown
- WordTraceId: 17171

###### 2.6.5.1.11[3]
- implement: false
- kind: Placeholder
- atomic: false
- Legal Obligation: not applicable
- WordTraceId: 17261

###### 2.6.5.1.11[3].[f]5
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- implement: false
- kind: Figure
- atomic: false
- Legal Obligation: not applicable
- WordTraceId: 17289

###### 2.6.5.1.11[3].[f]5.C
Figure {Figure 5}: ERTMS/ETCS Application Level 1 with infill function by Euroloop or Radio infill
- implementerEnhanced: Figure 5: ERTMS/ETCS Application Level 1 with infill function by
  Euroloop
  [EXTERNAL]
  or Radio infill
- PlainText: Figure 5: ERTMS/ETCS Application Level 1 with infill function by Euroloop or Radio infill
- implement: false
- kind: Figure
- atomic: true
- Legal Obligation: unknown
- WordTraceId: 17289

##### 2.6.5.2
Summary of characteristics of Application Level 1
- implement: false
- kind: Heading
- atomic: false
- Legal Obligation: not applicable
- WordTraceId: 17404

###### 2.6.5.2.1
Trackside equipment:
- implementerEnhanced: Trackside
  [EXTERNAL]
  equipment:
- implement: false
- kind: Heading
- atomic: true
- Legal Obligation: unknown
- WordTraceId: 17454

###### 2.6.5.2.1.*[1]
Eurobalises for spot transmission from track to train.
- implementerEnhanced: Eurobalises
  [EXTERNAL]
  for spot transmission from track to train.
- ListNumberText: ·
- implement: true
- kind: ordinary
- atomic: true
- Legal Obligation: unknown
- WordTraceId: 17476

###### 2.6.5.2.1.*[2]
Eurobalises must be able to transmit variable information.
- implementerEnhanced: Eurobalises
  [EXTERNAL]
  must be able to transmit variable information.
- ListNumberText: ·
- implement: true
- kind: ordinary
- atomic: true
- Legal Obligation: unknown
- WordTraceId: 17532

###### 2.6.5.2.1.*[3]
Semi continuous infill transmission by using Euroloop or radio infill is optional.
- implementerEnhanced: Semi continuous infill transmission by using
  Euroloop
  [EXTERNAL]
  or radio infill is optional.
- ListNumberText: ·
- implement: true
- kind: ordinary
- atomic: true
- Legal Obligation: unknown
- WordTraceId: 17591

###### 2.6.5.2.2
Main ERTMS/ETCS trackside function:
- implementerEnhanced: Main ERTMS/ETCS
  trackside
  [EXTERNAL]
  function:
- implement: false
- kind: Heading
- atomic: true
- Legal Obligation: unknown
- WordTraceId: 17674

###### 2.6.5.2.2.*[1]
Determine movement authorities according to the underlying signalling system.
- ListNumberText: ·
- implement: true
- kind: ordinary
- atomic: true
- Legal Obligation: unknown
- WordTraceId: 17710

###### 2.6.5.2.2.*[2]
Transmit movement authorities and track description data to the train.
- ListNumberText: ·
- implement: true
- kind: ordinary
- atomic: true
- Legal Obligation: unknown
- WordTraceId: 17788

###### 2.6.5.2.3
On-board equipment:
- implementerEnhanced: On-board equipment
  [SELF]
  :
- implement: false
- kind: Heading
- atomic: true
- Legal Obligation: unknown
- WordTraceId: 17861

###### 2.6.5.2.3.*[1]
Onboard equipment with Eurobalise transmission.
- implementerEnhanced: Onboard equipment
  [SELF]
  with
  Eurobalise
  [EXTERNAL]
  transmission.
- ListNumberText: ·
- implement: true
- kind: ordinary
- atomic: true
- Legal Obligation: unknown
- WordTraceId: 17881

###### 2.6.5.2.3.*[2]
Euroloop transmission if infill by Euroloop is required.
- implementerEnhanced: Euroloop
  [EXTERNAL]
  transmission
  if
  [CONDITION]
  infill by
  Euroloop
  [EXTERNAL]
  is required.
- ListNumberText: ·
- implement: true
- kind: ordinary
- atomic: true
- Legal Obligation: unknown
- WordTraceId: 17929

###### 2.6.5.2.3.*[3]
Radio infill transmission if infill by radio is required.
- implementerEnhanced: Radio infill transmission
  if
  [CONDITION]
  infill by radio is required.
- ListNumberText: ·
- implement: true
- kind: ordinary
- atomic: true
- Legal Obligation: unknown
- WordTraceId: 17986

###### 2.6.5.2.4
Main ERTMS/ETCS on-board function:
- implementerEnhanced: Main
  ERTMS/ETCS
  on-board
  [SELF]
  function:
- implement: false
- kind: Heading
- atomic: true
- Legal Obligation: unknown
- WordTraceId: 18044

###### 2.6.5.2.4.*[1]
Reception of movement authority and track description related to the transmitting balise.
- implementerEnhanced: Reception of movement authority and track description related to the transmitting
  balise
  [EXTERNAL]
  .
- ListNumberText: ·
- implement: true
- kind: ordinary
- atomic: true
- Legal Obligation: unknown
- WordTraceId: 18079

###### 2.6.5.2.4.*[2]
Selection of the most restrictive value of the different speeds permitted at each location ahead.
- ListNumberText: ·
- implement: true
- kind: ordinary
- atomic: true
- Legal Obligation: unknown
- WordTraceId: 18169

###### 2.6.5.2.4.*[3]
Calculation of a dynamic speed profile taking into account the train running/braking characteristics which are known on-board and the track description data.
- ListNumberText: ·
- implement: true
- kind: ordinary
- atomic: true
- Legal Obligation: unknown
- WordTraceId: 18267

###### 2.6.5.2.4.*[4]
Comparison of the train speed with the permitted speed and commanding of the brake application if necessary.
- implementerEnhanced: Comparison of the train speed with the permitted speed and commanding of the brake application
  if
  [CONDITION]
  necessary
  [WEAK]
  .
- ListNumberText: ·
- implement: true
- kind: ordinary
- atomic: true
- Legal Obligation: unknown
- WordTraceId: 18425

###### 2.6.5.2.4.*[5]
Cab signalling to the driver.
- implementerEnhanced: Cab signalling to the
  driver
  [EXTERNAL]
  .
- ListNumberText: ·
- implement: true
- kind: ordinary
- atomic: true
- Legal Obligation: unknown
- WordTraceId: 18535

#### 2.6.6
ERTMS/ETCS Application Level 2
- implement: false
- kind: Heading
- atomic: false
- Legal Obligation: not applicable
- WordTraceId: 18566

##### 2.6.6.1
General description
- implement: false
- kind: Heading
- atomic: false
- Legal Obligation: not applicable
- WordTraceId: 18597

###### 2.6.6.1.1
ERTMS/ETCS Level 2 is a radio based train control system which is used as an overlay on an underlying signalling system.
- implement: true
- kind: ordinary
- atomic: true
- Legal Obligation: unknown
- WordTraceId: 18617

###### 2.6.6.1.2
Movement authorities are generated trackside and are transmitted to the train via Euroradio.
- implementerEnhanced: Movement authorities are generated
  trackside
  [EXTERNAL]
  and are transmitted to the train via Euroradio.
- implement: true
- kind: ordinary
- atomic: true
- Legal Obligation: unknown
- WordTraceId: 18739

###### 2.6.6.1.3
ERTMS/ETCS Level 2 provides a continuous speed supervision system, which also protects against overrun of the authority.
- implement: true
- kind: ordinary
- atomic: true
- Legal Obligation: unknown
- WordTraceId: 18833

###### 2.6.6.1.4
Train detection and train integrity supervision are performed by the trackside equipment of the underlying signalling system (interlocking, track circuits etc.) and are outside the scope of ERTMS/ETCS.
- implementerEnhanced: Train detection and train integrity supervision are performed by the
  trackside
  [EXTERNAL]
  equipment of the underlying signalling system (interlocking, track circuits
  etc.
  [WEAK]
  ) and are outside the scope of ERTMS/ETCS.
- implement: true
- kind: ordinary
- atomic: true
- Legal Obligation: unknown
- WordTraceId: 18955

###### 2.6.6.1.5
Level 2 is based on Euroradio for track to train communication and on Eurobalises as spot transmission devices mainly for location referencing.
- implementerEnhanced: Level 2 is based on Euroradio for track to train communication and on
  Eurobalises
  [EXTERNAL]
  as spot transmission devices mainly for location referencing.
- implement: true
- kind: ordinary
- atomic: true
- Legal Obligation: unknown
- WordTraceId: 19157

###### 2.6.6.1.6
The trackside radio block centre which provides the information to the trains knows each ERTMS/ETCS controlled train individually by the ERTMS/ETCS identity of its leading ERTMS/ETCS on-board equipment.
- implementerEnhanced: The
  trackside
  [EXTERNAL]
  radio block centre
  [EXTERNAL]
  which provides the information to the trains knows each ERTMS/ETCS controlled train individually by the ERTMS/ETCS identity of its leading
  ERTMS/ETCS on-board equipment
  [SELF]
  .
- implement: true
- kind: ordinary
- atomic: true
- Legal Obligation: unknown
- WordTraceId: 19303

###### 2.6.6.1.7
Note: Lineside signals can be suppressed in Level 2.
- implement: false
- kind: Note
- atomic: false
- Legal Obligation: not applicable
- WordTraceId: 19507

###### 2.6.6.1.7[2]
- implement: false
- kind: Placeholder
- atomic: false
- Legal Obligation: not applicable
- WordTraceId: 19560

###### 2.6.6.1.7[2].[f]6
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- implement: false
- kind: Figure
- atomic: false
- Legal Obligation: not applicable
- WordTraceId: 19577

###### 2.6.6.1.7[2].[f]6.C
Figure {Figure 6}: ERTMS/ETCS Application Level 2
- implementerEnhanced: Figure 6: ERTMS/ETCS Application Level 2
- PlainText: Figure 6: ERTMS/ETCS Application Level 2
- implement: false
- kind: Figure
- atomic: true
- Legal Obligation: unknown
- WordTraceId: 19577

##### 2.6.6.2
Summary of characteristics of Application Level 2
- implement: false
- kind: Heading
- atomic: false
- Legal Obligation: not applicable
- WordTraceId: 19645

###### 2.6.6.2.1
Trackside equipment:
- implementerEnhanced: Trackside
  [EXTERNAL]
  equipment:
- implement: false
- kind: Heading
- atomic: true
- Legal Obligation: unknown
- WordTraceId: 19695

###### 2.6.6.2.1.*[1]
Radio block centre.
- implementerEnhanced: Radio block centre
  [EXTERNAL]
  .
- ListNumberText: ·
- implement: true
- kind: ordinary
- atomic: true
- Legal Obligation: unknown
- WordTraceId: 19717

###### 2.6.6.2.1.*[2]
Euroradio for bi-directional track-train communication.
- ListNumberText: ·
- implement: true
- kind: ordinary
- atomic: true
- Legal Obligation: unknown
- WordTraceId: 19737

###### 2.6.6.2.1.*[3]
Eurobalises mainly for location referencing.
- implementerEnhanced: Eurobalises
  [EXTERNAL]
  mainly for location referencing.
- ListNumberText: ·
- implement: true
- kind: ordinary
- atomic: true
- Legal Obligation: unknown
- WordTraceId: 19793

###### 2.6.6.2.2
Main ERTMS/ETCS trackside function:
- implementerEnhanced: Main ERTMS/ETCS
  trackside
  [EXTERNAL]
  function:
- implement: false
- kind: Heading
- atomic: true
- Legal Obligation: unknown
- WordTraceId: 19839

###### 2.6.6.2.2.*[1]
Knowing each train equipped with and running under ERTMS/ETCS within an RBC area by its ERTMS/ETCS identity.
- implementerEnhanced: Knowing each train equipped with and running under ERTMS/ETCS within an
  RBC
  [EXTERNAL]
  area by its ERTMS/ETCS identity.
- ListNumberText: ·
- implement: true
- kind: ordinary
- atomic: true
- Legal Obligation: unknown
- WordTraceId: 19875

###### 2.6.6.2.2.*[2]
Following each ERTMS/ETCS controlled train’s location within an RBC area.
- implementerEnhanced: Following each ERTMS/ETCS controlled train’s location within an
  RBC
  [EXTERNAL]
  area.
- ListNumberText: ·
- implement: true
- kind: ordinary
- atomic: true
- Legal Obligation: unknown
- WordTraceId: 19985

###### 2.6.6.2.2.*[3]
Determine movement authorities according to the underlying signalling system for each train individually.
- implementerEnhanced: Determine movement authorities according to the underlying signalling system
  for each
  [LOOP]
  train individually.
- ListNumberText: ·
- implement: true
- kind: ordinary
- atomic: true
- Legal Obligation: unknown
- WordTraceId: 20060

###### 2.6.6.2.2.*[4]
Transmit movement authorities and track description to each train individually.
- ListNumberText: ·
- implement: true
- kind: ordinary
- atomic: true
- Legal Obligation: unknown
- WordTraceId: 20166

###### 2.6.6.2.2.*[5]
Handing over of train control between different RBC’s at the RBC-RBC borders.
- ListNumberText: ·
- implement: true
- kind: ordinary
- atomic: true
- Legal Obligation: unknown
- WordTraceId: 20248

###### 2.6.6.2.3
On-board equipment:
- implementerEnhanced: On-board equipment
  [SELF]
  :
- implement: false
- kind: Heading
- atomic: true
- Legal Obligation: unknown
- WordTraceId: 20326

###### 2.6.6.2.3.*[1]
Onboard equipment with Eurobalise and Euroradio transmissions.
- implementerEnhanced: Onboard equipment
  [SELF]
  with
  Eurobalise
  [EXTERNAL]
  and Euroradio transmissions.
- ListNumberText: ·
- implement: true
- kind: ordinary
- atomic: true
- Legal Obligation: unknown
- WordTraceId: 20347

###### 2.6.6.2.4
Main ERTMS/ETCS on-board function:
- implementerEnhanced: Main
  ERTMS/ETCS
  on-board
  [SELF]
  function:
- implement: false
- kind: Heading
- atomic: true
- Legal Obligation: unknown
- WordTraceId: 20410

###### 2.6.6.2.4.*[1]
The train reads Eurobalises and sends its position relative to the detected balises to the radio block centre.
- implementerEnhanced: The train reads
  Eurobalises
  [EXTERNAL]
  and sends its position relative to the detected
  balises
  [EXTERNAL]
  to the
  radio block centre
  [EXTERNAL]
  .
- ListNumberText: ·
- implement: true
- kind: ordinary
- atomic: true
- Legal Obligation: unknown
- WordTraceId: 20445

###### 2.6.6.2.4.*[2]
The train receives a movement authority and the track description via Euroradio relating to a balise.
- implementerEnhanced: The train receives a movement authority and the track description via Euroradio relating to a
  balise
  [EXTERNAL]
  .
- ListNumberText: ·
- implement: true
- kind: ordinary
- atomic: true
- Legal Obligation: unknown
- WordTraceId: 20556

###### 2.6.6.2.4.*[3]
Selection of the most restrictive value of the different speeds permitted at each location ahead.
- ListNumberText: ·
- implement: true
- kind: ordinary
- atomic: true
- Legal Obligation: unknown
- WordTraceId: 20660

###### 2.6.6.2.4.*[4]
Calculation of a dynamic speed profile taking into account the train running/braking characteristics which are known on-board and the track description data.
- ListNumberText: ·
- implement: true
- kind: ordinary
- atomic: true
- Legal Obligation: unknown
- WordTraceId: 20758

###### 2.6.6.2.4.*[5]
Comparison of the train speed with the permitted speed and commanding of the brake application if necessary.
- implementerEnhanced: Comparison of the train speed with the permitted speed and commanding of the brake application
  if
  [CONDITION]
  necessary
  [WEAK]
  .
- ListNumberText: ·
- implement: true
- kind: ordinary
- atomic: true
- Legal Obligation: unknown
- WordTraceId: 20916

###### 2.6.6.2.4.*[6]
Cab signalling to the driver.
- implementerEnhanced: Cab signalling to the
  driver
  [EXTERNAL]
  .
- ListNumberText: ·
- implement: true
- kind: ordinary
- atomic: true
- Legal Obligation: unknown
- WordTraceId: 21026

#### 2.6.7
ERTMS/ETCS Application Level 3
- implement: false
- kind: Heading
- atomic: false
- Legal Obligation: not applicable
- WordTraceId: 21057

##### 2.6.7.1
General description
- implement: false
- kind: Heading
- atomic: false
- Legal Obligation: not applicable
- WordTraceId: 21088

###### 2.6.7.1.1
ERTMS/ETCS Level 3 is a radio based train control system.
- implement: true
- kind: ordinary
- atomic: true
- Legal Obligation: unknown
- WordTraceId: 21108

###### 2.6.7.1.2
Movement authorities are generated trackside and are transmitted to the train via Euroradio.
- implementerEnhanced: Movement authorities are generated
  trackside
  [EXTERNAL]
  and are transmitted to the train via Euroradio.
- implement: true
- kind: ordinary
- atomic: true
- Legal Obligation: unknown
- WordTraceId: 21166

###### 2.6.7.1.3
ERTMS/ETCS Level 3 provides a continuous speed supervision system, which also protects against overrun of the authority.
- implement: true
- kind: ordinary
- atomic: true
- Legal Obligation: unknown
- WordTraceId: 21260

###### 2.6.7.1.4
Train position and train integrity supervision are performed by the trackside radio block centre in co-operation with the train (which sends position reports and train integrity information).
- implementerEnhanced: Train position and train integrity supervision are performed by the
  trackside
  [EXTERNAL]
  radio block centre
  [EXTERNAL]
  in co-operation with the train (which sends position reports and train integrity information).
- implement: true
- kind: ordinary
- atomic: true
- Legal Obligation: unknown
- WordTraceId: 21382

###### 2.6.7.1.5
Level 3 is based on Euroradio for track to train communication and on Eurobalises as spot transmission devices mainly for location referencing.
- implementerEnhanced: Level 3 is based on Euroradio for track to train communication and on
  Eurobalises
  [EXTERNAL]
  as spot transmission devices mainly for location referencing.
- implement: true
- kind: ordinary
- atomic: true
- Legal Obligation: unknown
- WordTraceId: 21575

###### 2.6.7.1.6
The trackside radio block centre which provides the information to the trains knows each train individually by the ERTMS/ETCS identity of its leading ERTMS/ETCS on-board equipment.
- implementerEnhanced: The
  trackside
  [EXTERNAL]
  radio block centre
  [EXTERNAL]
  which provides the information to the trains knows each train individually by the ERTMS/ETCS identity of its leading
  ERTMS/ETCS on-board equipment
  [SELF]
  .
- implement: true
- kind: ordinary
- atomic: true
- Legal Obligation: unknown
- WordTraceId: 21721

###### 2.6.7.1.7
Note: Lineside signals are not foreseen to be used when operating in Level 3.
- implementerEnhanced: Note: Lineside signals are not foreseen to be used
  when
  [CONDITION]
  operating in Level 3.
- implement: false
- kind: Note
- atomic: false
- Legal Obligation: not applicable
- WordTraceId: 21903

###### 2.6.7.1.7[2]
- implement: false
- kind: Placeholder
- atomic: false
- Legal Obligation: not applicable
- WordTraceId: 21981

###### 2.6.7.1.7[2].[f]7
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- implement: false
- kind: Figure
- atomic: false
- Legal Obligation: not applicable
- WordTraceId: 21999

###### 2.6.7.1.7[2].[f]7.C
Figure {Figure 7}: ERTMS/ETCS Application Level 3
- implementerEnhanced: Figure 7: ERTMS/ETCS Application Level 3
- PlainText: Figure 7: ERTMS/ETCS Application Level 3
- implement: false
- kind: Figure
- atomic: true
- Legal Obligation: unknown
- WordTraceId: 21999

##### 2.6.7.2
Summary of characteristics of Application Level 3
- implement: false
- kind: Heading
- atomic: false
- Legal Obligation: not applicable
- WordTraceId: 22065

###### 2.6.7.2.1
Trackside equipment:
- implementerEnhanced: Trackside
  [EXTERNAL]
  equipment:
- implement: false
- kind: Heading
- atomic: true
- Legal Obligation: unknown
- WordTraceId: 22115

###### 2.6.7.2.1.*[1]
Radio block centre.
- implementerEnhanced: Radio block centre
  [EXTERNAL]
  .
- ListNumberText: ·
- implement: true
- kind: ordinary
- atomic: true
- Legal Obligation: unknown
- WordTraceId: 22137

###### 2.6.7.2.1.*[2]
Euroradio for bi-directional track-train communication.
- ListNumberText: ·
- implement: true
- kind: ordinary
- atomic: true
- Legal Obligation: unknown
- WordTraceId: 22157

###### 2.6.7.2.1.*[3]
Eurobalises for mainly location referencing.
- implementerEnhanced: Eurobalises
  [EXTERNAL]
  for mainly location referencing.
- ListNumberText: ·
- implement: true
- kind: ordinary
- atomic: true
- Legal Obligation: unknown
- WordTraceId: 22213

###### 2.6.7.2.2
Main ERTMS/ETCS trackside function:
- implementerEnhanced: Main ERTMS/ETCS
  trackside
  [EXTERNAL]
  function:
- implement: false
- kind: Heading
- atomic: true
- Legal Obligation: unknown
- WordTraceId: 22259

###### 2.6.7.2.2.*[1]
Knowing each train within an RBC area by its ERTMS/ETCS identity.
- implementerEnhanced: Knowing each train within an
  RBC
  [EXTERNAL]
  area by its ERTMS/ETCS identity.
- ListNumberText: ·
- implement: true
- kind: ordinary
- atomic: true
- Legal Obligation: unknown
- WordTraceId: 22295

###### 2.6.7.2.2.*[2]
Following each trains location within an RBC area.
- implementerEnhanced: Following each trains location within an
  RBC
  [EXTERNAL]
  area.
- ListNumberText: ·
- implement: true
- kind: ordinary
- atomic: true
- Legal Obligation: unknown
- WordTraceId: 22362

###### 2.6.7.2.2.*[3]
Route locking and route releasing based on information received from the trains.
- ListNumberText: ·
- implement: true
- kind: ordinary
- atomic: true
- Legal Obligation: unknown
- WordTraceId: 22414

###### 2.6.7.2.2.*[4]
Determine movement authorities for each train individually.
- implementerEnhanced: Determine movement authorities
  for each
  [LOOP]
  train individually.
- ListNumberText: ·
- implement: true
- kind: ordinary
- atomic: true
- Legal Obligation: unknown
- WordTraceId: 22495

###### 2.6.7.2.2.*[5]
Transmit movement authorities and track description to each train individually.
- ListNumberText: ·
- implement: true
- kind: ordinary
- atomic: true
- Legal Obligation: unknown
- WordTraceId: 22556

###### 2.6.7.2.2.*[6]
Handing over of train control between different RBC’s at the RBC-RBC borders.
- ListNumberText: ·
- implement: true
- kind: ordinary
- atomic: true
- Legal Obligation: unknown
- WordTraceId: 22638

###### 2.6.7.2.3
On-board equipment:
- implementerEnhanced: On-board equipment
  [SELF]
  :
- implement: false
- kind: Heading
- atomic: true
- Legal Obligation: unknown
- WordTraceId: 22716

###### 2.6.7.2.3.*[1]
Onboard equipment with Eurobalise and Euroradio transmissions.
- implementerEnhanced: Onboard equipment
  [SELF]
  with
  Eurobalise
  [EXTERNAL]
  and Euroradio transmissions.
- ListNumberText: ·
- implement: true
- kind: ordinary
- atomic: true
- Legal Obligation: unknown
- WordTraceId: 22737

###### 2.6.7.2.3.*[2]
Train integrity proving system.
- ListNumberText: ·
- implement: true
- kind: ordinary
- atomic: true
- Legal Obligation: unknown
- WordTraceId: 22800

###### 2.6.7.2.4
Main ERTMS/ETCS on-board functions:
- implementerEnhanced: Main
  ERTMS/ETCS
  on-board
  [SELF]
  functions:
- implement: false
- kind: Heading
- atomic: true
- Legal Obligation: unknown
- WordTraceId: 22832

###### 2.6.7.2.4.*[1]
The train reads Eurobalises and sends its position relative to the detected balises to the radio block centre.
- implementerEnhanced: The train reads
  Eurobalises
  [EXTERNAL]
  and sends its position relative to the detected
  balises
  [EXTERNAL]
  to the
  radio block centre
  [EXTERNAL]
  .
- ListNumberText: ·
- implement: true
- kind: ordinary
- atomic: true
- Legal Obligation: unknown
- WordTraceId: 22868

###### 2.6.7.2.4.*[2]
The train monitors train integrity (external function, not part of ERTMS/ETCS) and sends this information to the radio block centre.
- implementerEnhanced: The train monitors train integrity (
  external
  [EXTERNAL]
  function, not part of ERTMS/ETCS) and sends this information to the
  radio block centre
  [EXTERNAL]
  .
- ListNumberText: ·
- implement: true
- kind: ordinary
- atomic: true
- Legal Obligation: unknown
- WordTraceId: 22979

###### 2.6.7.2.4.*[3]
The train receives a movement authority and the track description via Euroradio relating to a balise.
- implementerEnhanced: The train receives a movement authority and the track description via Euroradio relating to a
  balise
  [EXTERNAL]
  .
- ListNumberText: ·
- implement: true
- kind: ordinary
- atomic: true
- Legal Obligation: unknown
- WordTraceId: 23112

###### 2.6.7.2.4.*[4]
Selection of the most restrictive value of the different speeds permitted at each location ahead.
- ListNumberText: ·
- implement: true
- kind: ordinary
- atomic: true
- Legal Obligation: unknown
- WordTraceId: 23216

###### 2.6.7.2.4.*[5]
Calculation of a dynamic speed profile, taking into account the train running/braking characteristics which are known on-board and the track description data.
- ListNumberText: ·
- implement: true
- kind: ordinary
- atomic: true
- Legal Obligation: unknown
- WordTraceId: 23314

###### 2.6.7.2.4.*[6]
Comparison of the train speed with the permitted speed and commanding of the brake application if necessary.
- implementerEnhanced: Comparison of the train speed with the permitted speed and commanding of the brake application
  if
  [CONDITION]
  necessary
  [WEAK]
  .
- ListNumberText: ·
- implement: true
- kind: ordinary
- atomic: true
- Legal Obligation: unknown
- WordTraceId: 23473

###### 2.6.7.2.4.*[7]
Cab signalling to the driver.
- implementerEnhanced: Cab signalling to the
  driver
  [EXTERNAL]
  .
- ListNumberText: ·
- implement: true
- kind: ordinary
- atomic: true
- Legal Obligation: unknown
- WordTraceId: 23583

#### 2.6.8
Level transitions
- implement: false
- kind: Heading
- atomic: false
- Legal Obligation: not applicable
- WordTraceId: 23614

##### 2.6.8.1
An ERTMS/ETCS equipment which is not isolated always operates in one of the above described levels. All transitions between these levels are performed according to defined functions and procedures.
- implementerEnhanced: An ERTMS/ETCS equipment which is not isolated always operates in one of the
  above
  [WEAK]
  described levels. All transitions between these levels are performed according to defined functions and procedures.
- implement: true
- kind: ordinary
- atomic: false
- Legal Obligation: unknown
- WordTraceId: 23632

##### 2.6.8.2
Additional national functions and rules which might be used by an individual railway to for example prevent not equipped trains from entering a level 2/3 area are not specified here and have to be implemented outside ERTMS/ETCS.
- implementerEnhanced: Additional national functions and rules which might be used by an individual railway to
  for example
  [WEAK]
  prevent not equipped trains from entering a level 2/3 area are not specified here and have to be implemented outside ERTMS/ETCS.
- implement: true
- kind: ordinary
- atomic: true
- Legal Obligation: unknown
- WordTraceId: 23831

##### 2.6.8.3
The following table shows all possible transitions (marked with Grey):
- implement: true
- kind: ordinary
- atomic: true
- Legal Obligation: unknown
- WordTraceId: 24060

##### 2.6.8.3[2]
- implement: false
- kind: Placeholder
- atomic: false
- Legal Obligation: not applicable
- WordTraceId: 24131

###### 2.6.8.3[2].[t]1
| [r][1].[c][1] to from | [r][1].[c][2] 0 | [r][1].[c][3] NTC | [r][1].[c][4] 1 | [r][1].[c][5] 2 | [r][1].[c][6] 3 |
| --- | --- | --- | --- | --- | --- |
| [r][2].[c][1] 0 | [r][2].[c][2] | [r][2].[c][3] | [r][2].[c][4] | [r][2].[c][5] | [r][2].[c][6] |
| [r][3].[c][1] NTC | [r][3].[c][2] | [r][3].[c][3] a) | [r][3].[c][4] | [r][3].[c][5] | [r][3].[c][6] |
| [r][4].[c][1] 1 | [r][4].[c][2] | [r][4].[c][3] | [r][4].[c][4] | [r][4].[c][5] | [r][4].[c][6] |
| [r][5].[c][1] 2 | [r][5].[c][2] | [r][5].[c][3] | [r][5].[c][4] | [r][5].[c][5] b) | [r][5].[c][6] |
| [r][6].[c][1] 3 | [r][6].[c][2] | [r][6].[c][3] | [r][6].[c][4] | [r][6].[c][5] | [r][6].[c][6] b) |
- implement: false
- kind: Table
- atomic: false
- Legal Obligation: not applicable
- WordTraceId: 24217

###### 2.6.8.3[2].[t]1.C
Table {Table 1}: Possible level transitions.
- implementerEnhanced: Table 1: Possible level transitions.
- PlainText: Table 1: Possible level transitions.
- implement: false
- kind: Table
- atomic: true
- Legal Obligation: unknown
- WordTraceId: 24217

###### 2.6.8.3[2].[t]1.[r][1]
- implement: false
- kind: Table
- atomic: false
- Legal Obligation: not applicable
- WordTraceId: 24131

###### 2.6.8.3[2].[t]1.[r][1].[c][1]
CONTENTS HAVE BEEN SPLIT UP - SEE CHILDREN
- implement: false
- kind: ordinary
- atomic: false
- Legal Obligation: not applicable
- WordTraceId: 24131

###### 2.6.8.3[2].[t]1.[r][1].[c][1].[1]
to
- implement: true
- kind: ordinary
- atomic: true
- Legal Obligation: unknown
- WordTraceId: 24131

###### 2.6.8.3[2].[t]1.[r][1].[c][1].[2]
from
- implement: true
- kind: ordinary
- atomic: true
- Legal Obligation: unknown
- WordTraceId: 24134

###### 2.6.8.3[2].[t]1.[r][1].[c][2]
0
- implement: true
- kind: ordinary
- atomic: true
- Legal Obligation: unknown
- WordTraceId: 24156

###### 2.6.8.3[2].[t]1.[r][1].[c][3]
NTC
- implement: true
- kind: ordinary
- atomic: true
- Legal Obligation: unknown
- WordTraceId: 24158

###### 2.6.8.3[2].[t]1.[r][1].[c][4]
1
- implement: true
- kind: ordinary
- atomic: true
- Legal Obligation: unknown
- WordTraceId: 24162

###### 2.6.8.3[2].[t]1.[r][1].[c][5]
2
- implement: true
- kind: ordinary
- atomic: true
- Legal Obligation: unknown
- WordTraceId: 24164

###### 2.6.8.3[2].[t]1.[r][1].[c][6]
3
- implement: true
- kind: ordinary
- atomic: true
- Legal Obligation: unknown
- WordTraceId: 24166

###### 2.6.8.3[2].[t]1.[r][2]
- implement: false
- kind: Table
- atomic: false
- Legal Obligation: not applicable
- WordTraceId: 24169

###### 2.6.8.3[2].[t]1.[r][2].[c][1]
0
- implement: true
- kind: ordinary
- atomic: true
- Legal Obligation: unknown
- WordTraceId: 24169

###### 2.6.8.3[2].[t]1.[r][2].[c][2]
- implement: true
- kind: ordinary
- atomic: true
- Legal Obligation: unknown
- WordTraceId: 24171

###### 2.6.8.3[2].[t]1.[r][2].[c][3]
- implement: true
- kind: ordinary
- atomic: true
- Legal Obligation: unknown
- WordTraceId: 24172

###### 2.6.8.3[2].[t]1.[r][2].[c][4]
- implement: true
- kind: ordinary
- atomic: true
- Legal Obligation: unknown
- WordTraceId: 24173

###### 2.6.8.3[2].[t]1.[r][2].[c][5]
- implement: true
- kind: ordinary
- atomic: true
- Legal Obligation: unknown
- WordTraceId: 24174

###### 2.6.8.3[2].[t]1.[r][2].[c][6]
- implement: true
- kind: ordinary
- atomic: true
- Legal Obligation: unknown
- WordTraceId: 24175

###### 2.6.8.3[2].[t]1.[r][3]
- implement: false
- kind: Table
- atomic: false
- Legal Obligation: not applicable
- WordTraceId: 24177

###### 2.6.8.3[2].[t]1.[r][3].[c][1]
NTC
- implement: true
- kind: ordinary
- atomic: true
- Legal Obligation: unknown
- WordTraceId: 24177

###### 2.6.8.3[2].[t]1.[r][3].[c][2]
- implement: true
- kind: ordinary
- atomic: true
- Legal Obligation: unknown
- WordTraceId: 24181

###### 2.6.8.3[2].[t]1.[r][3].[c][3]
a)
- implement: true
- kind: ordinary
- atomic: true
- Legal Obligation: unknown
- WordTraceId: 24182

###### 2.6.8.3[2].[t]1.[r][3].[c][4]
- implement: true
- kind: ordinary
- atomic: true
- Legal Obligation: unknown
- WordTraceId: 24185

###### 2.6.8.3[2].[t]1.[r][3].[c][5]
- implement: true
- kind: ordinary
- atomic: true
- Legal Obligation: unknown
- WordTraceId: 24186

###### 2.6.8.3[2].[t]1.[r][3].[c][6]
- implement: true
- kind: ordinary
- atomic: true
- Legal Obligation: unknown
- WordTraceId: 24187

###### 2.6.8.3[2].[t]1.[r][4]
- implement: false
- kind: Table
- atomic: false
- Legal Obligation: not applicable
- WordTraceId: 24189

###### 2.6.8.3[2].[t]1.[r][4].[c][1]
1
- implement: true
- kind: ordinary
- atomic: true
- Legal Obligation: unknown
- WordTraceId: 24189

###### 2.6.8.3[2].[t]1.[r][4].[c][2]
- implement: true
- kind: ordinary
- atomic: true
- Legal Obligation: unknown
- WordTraceId: 24191

###### 2.6.8.3[2].[t]1.[r][4].[c][3]
- implement: true
- kind: ordinary
- atomic: true
- Legal Obligation: unknown
- WordTraceId: 24192

###### 2.6.8.3[2].[t]1.[r][4].[c][4]
- implement: true
- kind: ordinary
- atomic: true
- Legal Obligation: unknown
- WordTraceId: 24193

###### 2.6.8.3[2].[t]1.[r][4].[c][5]
- implement: true
- kind: ordinary
- atomic: true
- Legal Obligation: unknown
- WordTraceId: 24194

###### 2.6.8.3[2].[t]1.[r][4].[c][6]
- implement: true
- kind: ordinary
- atomic: true
- Legal Obligation: unknown
- WordTraceId: 24195

###### 2.6.8.3[2].[t]1.[r][5]
- implement: false
- kind: Table
- atomic: false
- Legal Obligation: not applicable
- WordTraceId: 24197

###### 2.6.8.3[2].[t]1.[r][5].[c][1]
2
- implement: true
- kind: ordinary
- atomic: true
- Legal Obligation: unknown
- WordTraceId: 24197

###### 2.6.8.3[2].[t]1.[r][5].[c][2]
- implement: true
- kind: ordinary
- atomic: true
- Legal Obligation: unknown
- WordTraceId: 24199

###### 2.6.8.3[2].[t]1.[r][5].[c][3]
- implement: true
- kind: ordinary
- atomic: true
- Legal Obligation: unknown
- WordTraceId: 24200

###### 2.6.8.3[2].[t]1.[r][5].[c][4]
- implement: true
- kind: ordinary
- atomic: true
- Legal Obligation: unknown
- WordTraceId: 24201

###### 2.6.8.3[2].[t]1.[r][5].[c][5]
b)
- implement: true
- kind: ordinary
- atomic: true
- Legal Obligation: unknown
- WordTraceId: 24202

###### 2.6.8.3[2].[t]1.[r][5].[c][6]
- implement: true
- kind: ordinary
- atomic: true
- Legal Obligation: unknown
- WordTraceId: 24205

###### 2.6.8.3[2].[t]1.[r][6]
- implement: false
- kind: Table
- atomic: false
- Legal Obligation: not applicable
- WordTraceId: 24207

###### 2.6.8.3[2].[t]1.[r][6].[c][1]
3
- implement: true
- kind: ordinary
- atomic: true
- Legal Obligation: unknown
- WordTraceId: 24207

###### 2.6.8.3[2].[t]1.[r][6].[c][2]
- implement: true
- kind: ordinary
- atomic: true
- Legal Obligation: unknown
- WordTraceId: 24209

###### 2.6.8.3[2].[t]1.[r][6].[c][3]
- implement: true
- kind: ordinary
- atomic: true
- Legal Obligation: unknown
- WordTraceId: 24210

###### 2.6.8.3[2].[t]1.[r][6].[c][4]
- implement: true
- kind: ordinary
- atomic: true
- Legal Obligation: unknown
- WordTraceId: 24211

###### 2.6.8.3[2].[t]1.[r][6].[c][5]
- implement: true
- kind: ordinary
- atomic: true
- Legal Obligation: unknown
- WordTraceId: 24212

###### 2.6.8.3[2].[t]1.[r][6].[c][6]
b)
- implement: true
- kind: ordinary
- atomic: true
- Legal Obligation: unknown
- WordTraceId: 24213

###### 2.6.8.3[2].a
Transitions between level NTC and level NTC describe the switching from one national system to another national system.
- implementerEnhanced: Transitions between level NTC and level
  NTC
  describe the switching from one
  national system
  [EXTERNAL]
  to another
  national system
  [EXTERNAL]
  .
- ListNumberText: a)
- implement: true
- kind: ordinary
- atomic: true
- Legal Obligation: unknown
- WordTraceId: 24278

###### 2.6.8.3[2].b
Transitions between level 2 and level 2 respectively between level 3 and level 3 describe the handover between RBC’s.
- ListNumberText: b)
- implement: true
- kind: ordinary
- atomic: true
- Legal Obligation: unknown
- WordTraceId: 24399
