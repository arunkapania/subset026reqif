# TODO_FIND_A_NAME-

# Specification: Specification Document
- Description: Requirements TODO_FIND_A_NAME-

### 8
System Requirements Specification Chapter 8
Messages
- WordTraceId: 16

#### 8.1
Modification History
- WordTraceId: 130

#### 8.1[2]
- WordTraceId: 151

##### 8.1[2].[t]*
| Issue Number Date | Section Number | Modification / Description | Author |
| --- | --- | --- | --- |
| 0.0.1 990715 | All | Creation of the document “Clean version” based on SRS Class P Ch. 8 | V. Roger |
| 0.0.2 990716 | All | Update to SRS Class 1 | V. Roger |
| 0.1.0 990727 | All | Update considering review comments from ADT and ALS | V. Roger |
| 1.0.0 990729 | Version number and editorial changes. | Finalisation meeting, Stuttgart 990729. | HE |
| 1.2.0 990730 | Version number | Release version | HE |
| 1.2.1 991124 | Sections 8.4 to 8.7 | ECSAG comments (on chapter 8) taken into account. | V. Roger |
| 1.2.2 991209 | Sections 8.4 to 8.7. Creation of appendix. | Upsate to SRS Class 1 version 2 – First release | V. Roger |
| 1.3.0 991217 | Sections 8.4 to 8.7. Suppression of appendix. | Upsate to SRS Class 1 version 2 – Unisig Review (991216) | V. Roger |
| 1.3.1 991220 | Section 8.7.14 | Add Q_SCALE | P. Rimbaud |
| 2.0.0 991222 | Minor editorial changes | Release version | Ch. Frerichs (ed.) |
| 2.0.1 001002 | All | Corrections after UNISIG review 15 June 00 | P. Rimbaud |
| 2.1.0 001026 | Sections 8.4.1, 8.4.2, 8.4.3, 8.4.4, 8.5.1, 8.5.2, 8.5.3, 8.6, 8.7 | Corrections after UNISIG review 10/11 October 00 | P. Rimbaud |
| 2.2.0 | Packet 71 deleted, NID_C 10 bit | UNISIG release | SAB |
| 2.2.2 | Packet 71 added, messages 42 and 158 deleted | SUBSET-026 Corrected Paragraphs, Issue 2.2.2 | JY. Riou |
| 2.2.4 – 040512 |  | UNISIG Change Request according the scope defined in the 06/05/2004 e-mail | JY. RIOU |
| 2.2.4 SG checked 28/05/04 | Including all CLRs agreed with EEIG (see “List of CLRs agreed with EEIG for SRS v2.2.4” dated 28/05/04) Affected clauses see change marks |  | H. Kast |
| 2.2.5 21/01/05 | Incorporation of solution proposal for CLR 007 with EEIG users group comments |  | A. Hougardy |
| 2.2.6 04/02/05 | § 8.4.2.1, § 8.4.3.1, § 8.7.12 according to CR242 § 8.4.4.4.1.1, § 8.5.3, § 8.7.22 according to CR458 § 8.6.3 according to CR 487 |  | JY. RIOU |
| 2.2.7 01/08/05 | § 8.7.22 error correction (Q_ORIENTATION) according to CR458, § 8.4.4.4.2 according to CR 126 § 8.4.4.4.3 b), § 8.6.17 according to CR 299 § 8.4.1.4.5, § 8.4.4.4.1 according to CR 413 § 8.4.1.4.6 according to CR 633 |  | JY.RIOU |
| 2.2.8 30/11/05 | Change marks cleaned up and updated according to last CR decisions (including split of CRs 7 and 126) |  | JY. RIOU |
| 2.2.9 24/02/06 | Including all CR s that are classified as “IN” per Subset-108 version 1.0.0 Removal of all CRs that are not classified as “IN” as per SUBSET-108 version 1.0.0 with the exception of the CR 63, 98, 120, 158 and 538 |  | JY. RIOU |
| 2.3.0 24/02/06 | Release version |  | HK |
| 2.3.1 14/06/2006 | § 8.4.4.4.1 and § 8.7.5: “SRS v2.3.0 Release Note CR 382” point, § 8.4.4.4.3 b) and 8.6.17: removing of premature CR299 update |  | JY. RIOU |
| 2.3.2 17 / 03 /08 | Including all CRs that are in state “Analysis completed” according to ERA CCM |  | A. Hougardy |
| 2. 9 . 1 0 6 / 10 /08 | Including all enhancement CR’s retained for 3.0.0 baseline and all other error CR’s that are in state “Analysis completed” according to ERA CCM For editorial reasons, the following CR’s are also included: CR656, CR804, CR821 |  | A. Hougardy |
| 3.0.0 23 /12/08 | Release version |  | A. Hougardy |
| 3.0.1 22 /1 2 /09 | Including the results of the editorial review of the SRS 3.0.0 and the other error CR’s that are in state “Analysis completed” according to ERA CCM |  | A. Hougardy |
| 3.1.0 22 /02/10 | Release version |  | A. Hougardy |
| 3.1.1 08 / 11 /10 | Including all CR’s that are in state “Analysis completed” according to ERA CCM , plus CR731. |  | A. Hougardy |
| 3.2.0 22 /12/10 | Release version |  | A. Hougardy |
| 3.2.1 13 /12/11 | Including all CR’s that are in state “Analysis completed” according to ERA CCM |  | A. Hougardy |
| 3.3.0 0 7 /0 3 /12 | Baseline 3 release version |  | A. Hougardy |
- WordTraceId: 3702

#### 8.2
Table of Contents
- WordTraceId: 3702

#### 8.3
Introduction
- WordTraceId: 9610

##### 8.3.1
Scope and Purpose
- WordTraceId: 9623

###### 8.3.1.1
This chapter defines the format and content of messages necessary for ERTMS/ETCS functions.
- WordTraceId: 9641

###### 8.3.1.2
Concerning the transmission media, this chapter does not cover considerations such as medium-specific use constraints (e .g . distance between track-circuit and balise…), as well as functions (e .g . detection of balise reference, time and location stamp, identifying type of receiving balise, Key Management, Releasing/maintaining a radio connection…) and performance of the transmission media.
- PlainText: Concerning the transmission media, this chapter does not cover considerations such as medium-specific use constraints (e.g. distance between track-circuit and balise…), as well as functions (e.g. detection of balise reference, time and location stamp, identifying type of receiving balise, Key Management, Releasing/maintaining a radio connection…) and performance of the transmission media.
- WordTraceId: 9733

##### 8.3.2
Definitions
- WordTraceId: 10125

###### 8.3.2.1
Transmission media considered hereafter are standard ERTMS/ETCS transmission media used for ETCS (Eurobalise, Euroradio and Euroloop).
- WordTraceId: 10137

###### 8.3.2.2
A message includes user data (application level) and protocol data (depending on the transmission medium).
- WordTraceId: 10272

###### 8.3.2.3
A Eurobalise message is the information sent by a balise group (i.e. the message is composed of one or several telegrams , sorted by balise number in the group (telegram from balise number 1 first), ea ch telegram is transmitted by a Eurobalise). A Eurobalise telegram contains one header and an identified and coherent set of Packets.
- PlainText: A Eurobalise message is the information sent by a balise group (i.e. the message is composed of one or several telegrams, sorted by balise number in the group (telegram from balise number 1 first), each telegram is transmitted by a Eurobalise). A Eurobalise telegram contains one header and an identified and coherent set of Packets.
- WordTraceId: 10379

###### 8.3.2.3[2]
- WordTraceId: 10714

###### 8.3.2.3[2].[f][1]
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- WordTraceId: 10739

###### 8.3.2.3[2].[f][1].C
Figure {Figure 1}
: Composition of a balise group message
- PlainText: Figure 1: Composition of a balise group message
- WordTraceId: 10739

###### 8.3.2.4
A Euroradio message contains one header and an identified and coherent set of variables (if needed) and Packets.
- WordTraceId: 10813

###### 8.3.2.5
A Euroloop message contains one header and an identified and coherent set of Packets.
- WordTraceId: 10926

#### 8.4
Rules
- WordTraceId: 11012

##### 8.4.1
Common Rules
- WordTraceId: 11018

###### 8.4.1.1
A message (Euroradio/Euroloop) or telegram (Eurobalise) shall be composed of
- WordTraceId: 11031

###### 8.4.1.1.1
One Header,
- ListNumberText: 1.
- WordTraceId: 11108

###### 8.4.1.1.2
When needed, a predefined set of variables (only for Radio),
- ListNumberText: 2.
- WordTraceId: 11120

###### 8.4.1.1.3
When needed, a predefined set of Packets (only for Radio),
- ListNumberText: 3.
- WordTraceId: 11181

###### 8.4.1.1.4
Optional Packets as needed by application.
- ListNumberText: 4.
- WordTraceId: 11240

###### 8.4.1.2
The transmission order shall respect the order of data elements listed in the message format (from top to bottom).
- WordTraceId: 11283

###### 8.4.1.3
The behaviour of the receiver shall not depend on the sequence of the Packets given by the message.
- WordTraceId: 11398

###### 8.4.1.3.1
Exception for Infill information: The locations given in the packets following packet 136 (Infill Location Reference) shall be referred to the balise group indicated in such packet.
- WordTraceId: 11498

###### 8.4.1.3.2
Note: orientations are in any case always referred to the directionality of balise group (balise transmission), directionality of loop (Euroloop transmission) or directionality of LRBG (radio transmission).
- WordTraceId: 11680

###### 8.4.1.4
It shall be forbidden to send more instances of the same packet type for the same direction in the same message.
- WordTraceId: 11887

###### 8.4.1.4.1
Exception 1: A message can contain several packets 44 (Data used by applications outside the ERTMS/ETCS system).
- WordTraceId: 12000

###### 8.4.1.4.2
Exception 2: A message can contain several packets 65 (Temporary Speed Restriction). In case of revocable TSRs, the identities of the corresponding temporary speed restrictions (variable NID_TSR) transmitted in the same message shall be different.
- WordTraceId: 12113

###### 8.4.1.4.3
Exception 3: A message can contain several packets 66 (TSR Revocation). The identities of the corresponding temporary speed restrictions (variable NID_TSR) transmitted in the same message shall be different.
- WordTraceId: 12361

###### 8.4.1.4.4
Exception 4: A message transmitted by a balise group can contain one packet 136 per balise telegram per direction. Each packet 136 indicates which part of that telegram is to be considered as part of the infill information. Multiple packets 136 in balises of a balise group shall have identical content per direction.
- WordTraceId: 12569

###### 8.4.1.4.5
Exception 5: A message can contain several packets 88 (Level Crossing information). The identities of the corresponding Level Crossings (variable NID_LX) transmitted in the same message shall be different.
- WordTraceId: 12887

###### 8.4.1.4.6
Exception 6: A message transmitted by a balise group can contain several packets 254 (default balise , loop or RIU information).
- PlainText: Exception 6: A message transmitted by a balise group can contain several packets 254 (default balise, loop or RIU information).
- WordTraceId: 13093

###### 8.4.1.4.7
Exception 7 : A message transmitted by a balise group can contain several packets 145 (Inhibition of balise group message consistency reaction).
- PlainText: Exception 7: A message transmitted by a balise group can contain several packets 145 (Inhibition of balise group message consistency reaction).
- WordTraceId: 13221

###### 8.4.1.4.8
Exception 8: A message transmitted by a balise group can contain several packets 0 (Virtual Balise Cover marker).
- WordTraceId: 13365

###### 8.4.1.4.9
Exception 9: A message transmitted by a balise group can contain several packets 6 ( Virtual Balise Cover order ). The identities (pairs of variables NID_VBCMK and NID_C) of the corresponding VBC transmitted in the same message shall be different.
- PlainText: Exception 9: A message transmitted by a balise group can contain several packets 6 (Virtual Balise Cover order). The identities (pairs of variables NID_VBCMK and NID_C) of the corresponding VBC transmitted in the same message shall be different.
- WordTraceId: 13479

##### 8.4.2
Rules for Eurobalise telegrams
- WordTraceId: 13727

###### 8.4.2.1
The format of the telegram to be transmitted by each balise is as follows:
- WordTraceId: 13758

###### 8.4.2.1[2]
- WordTraceId: 13835

###### 8.4.2.1[2].[t]*
| General Format of Balise Telegram |  |  |  |  |
| --- | --- | --- | --- | --- |
| Field No. | VARIABLE | Length ( bits) | Remarks |  |
| [r][3].Field 1 | [r][3].Variable Q_UPDOWN | [r][3].Length 1 | [r][3].Remarks Defines the direction of the information: Down-link telegram (train to track) (0) Up-link telegram (track to train) (1) |  |
| [r][4].Field 2 | [r][4].Variable M_VERSION | [r][4].Length 7 | [r][4].Remarks Version of the ERTMS/ETCS system . |  |
| [r][5].Field 3 | [r][5].Variable Q_MEDIA | [r][5].Length 1 | [r][5].Remarks Defines the type of media: Balise (0) |  |
| [r][6].Field 4 | [r][6].Variable N_PIG | [r][6].Length 3 | [r][6].Remarks Position in the group. Defines the position of the balise in the balise group. |  |
| [r][7].Field 5 | [r][7].Variable N_TOTAL | [r][7].Length 3 | [r][7].Remarks Total number of balises in the balise group |  |
| [r][8].Field 6 | [r][8].Variable M_DUP | [r][8].Length 2 | [r][8].Remarks Used to indicate whether the information of the balise is a duplicate of the balise before or after this one. |  |
| [r][9].Field 7 | [r][9].Variable M_MCOUNT | [r][9].Length 8 | [r][9].Remarks Message counter (M_MCOUNT) - 8 bits. To enable detection of a change of balise group message during passage of the balise group. |  |
| [r][10].Field 8 | [r][10].Variable NID_C | [r][10].Length 10 | [r][10].Remarks Country or region. |  |
| [r][11].Field 9 | [r][11].Variable NID_BG | [r][11].Length 14 | [r][11].Remarks Identity of the balise group. |  |
| [r][12].Field 10 | [r][12].Variable Q_LINK | [r][12].Length 1 | [r][12].Remarks Marks the balise group as linked (Q_LINK = 1) or unlinked (Q_LINK = 0) |  |
| [r][13].Field | [r][13].Variable Packet 0 (optional) | [r][13].Length 14 | [r][13].Remarks Virtual Balise Cover marker |  |
| [r][14].Field | [r][14].Variable Information | [r][14].Length Variable | [r][14].Remarks This information is composed according to the rules applicable for packets. |  |
| [r][15].Field | [r][15].Variable Packet 255 | [r][15].Length 8 | [r][15].Remarks Finishing flag of the telegram |  |
- WordTraceId: 14919

###### 8.4.2.1[2].[t]*.[r][3]
- WordTraceId: 13913

###### 8.4.2.1[2].[t]*.[r][3].Field
1
- WordTraceId: 13913

###### 8.4.2.1[2].[t]*.[r][3].Variable
Q_UPDOWN
- WordTraceId: 13915

###### 8.4.2.1[2].[t]*.[r][3].Length
1
- WordTraceId: 13924

###### 8.4.2.1[2].[t]*.[r][3].Remarks
Defines the direction of the information:
Down-link telegram (train to track) (0)
Up-link telegram (track to train) (1)
- WordTraceId: 13926

###### 8.4.2.1[2].[t]*.[r][4]
- WordTraceId: 14049

###### 8.4.2.1[2].[t]*.[r][4].Field
2
- WordTraceId: 14049

###### 8.4.2.1[2].[t]*.[r][4].Variable
M_VERSION
- WordTraceId: 14051

###### 8.4.2.1[2].[t]*.[r][4].Length
7
- WordTraceId: 14061

###### 8.4.2.1[2].[t]*.[r][4].Remarks
Version of the ERTMS/ETCS system .
- PlainText: Version of the ERTMS/ETCS system.
- WordTraceId: 14063

###### 8.4.2.1[2].[t]*.[r][5]
- WordTraceId: 14098

###### 8.4.2.1[2].[t]*.[r][5].Field
3
- WordTraceId: 14098

###### 8.4.2.1[2].[t]*.[r][5].Variable
Q_MEDIA
- WordTraceId: 14100

###### 8.4.2.1[2].[t]*.[r][5].Length
1
- WordTraceId: 14108

###### 8.4.2.1[2].[t]*.[r][5].Remarks
Defines the type of media: Balise (0)
- WordTraceId: 14110

###### 8.4.2.1[2].[t]*.[r][6]
- WordTraceId: 14149

###### 8.4.2.1[2].[t]*.[r][6].Field
4
- WordTraceId: 14149

###### 8.4.2.1[2].[t]*.[r][6].Variable
N_PIG
- WordTraceId: 14152

###### 8.4.2.1[2].[t]*.[r][6].Length
3
- WordTraceId: 14158

###### 8.4.2.1[2].[t]*.[r][6].Remarks
Position in the group. Defines the position of the balise in the balise group.
- WordTraceId: 14160

###### 8.4.2.1[2].[t]*.[r][7]
- WordTraceId: 14240

###### 8.4.2.1[2].[t]*.[r][7].Field
5
- WordTraceId: 14240

###### 8.4.2.1[2].[t]*.[r][7].Variable
N_TOTAL
- WordTraceId: 14242

###### 8.4.2.1[2].[t]*.[r][7].Length
3
- WordTraceId: 14250

###### 8.4.2.1[2].[t]*.[r][7].Remarks
Total number of balises in the balise group
- WordTraceId: 14252

###### 8.4.2.1[2].[t]*.[r][8]
- WordTraceId: 14297

###### 8.4.2.1[2].[t]*.[r][8].Field
6
- WordTraceId: 14297

###### 8.4.2.1[2].[t]*.[r][8].Variable
M_DUP
- WordTraceId: 14299

###### 8.4.2.1[2].[t]*.[r][8].Length
2
- WordTraceId: 14305

###### 8.4.2.1[2].[t]*.[r][8].Remarks
Used to indicate whether the information of the balise is a duplicate of the balise before or after this one.
- WordTraceId: 14307

###### 8.4.2.1[2].[t]*.[r][9]
- WordTraceId: 14419

###### 8.4.2.1[2].[t]*.[r][9].Field
7
- WordTraceId: 14419

###### 8.4.2.1[2].[t]*.[r][9].Variable
M_MCOUNT
- WordTraceId: 14421

###### 8.4.2.1[2].[t]*.[r][9].Length
8
- WordTraceId: 14430

###### 8.4.2.1[2].[t]*.[r][9].Remarks
Message counter (M_MCOUNT) - 8 bits. To enable detection of a change of balise group message during passage of the balise group.
- WordTraceId: 14432

###### 8.4.2.1[2].[t]*.[r][10]
- WordTraceId: 14562

###### 8.4.2.1[2].[t]*.[r][10].Field
8
- WordTraceId: 14562

###### 8.4.2.1[2].[t]*.[r][10].Variable
NID_C
- WordTraceId: 14564

###### 8.4.2.1[2].[t]*.[r][10].Length
10
- WordTraceId: 14570

###### 8.4.2.1[2].[t]*.[r][10].Remarks
Country or region.
- WordTraceId: 14573

###### 8.4.2.1[2].[t]*.[r][11]
- WordTraceId: 14593

###### 8.4.2.1[2].[t]*.[r][11].Field
9
- WordTraceId: 14593

###### 8.4.2.1[2].[t]*.[r][11].Variable
NID_BG
- WordTraceId: 14595

###### 8.4.2.1[2].[t]*.[r][11].Length
14
- WordTraceId: 14602

###### 8.4.2.1[2].[t]*.[r][11].Remarks
Identity of the balise group.
- WordTraceId: 14605

###### 8.4.2.1[2].[t]*.[r][12]
- WordTraceId: 14636

###### 8.4.2.1[2].[t]*.[r][12].Field
10
- WordTraceId: 14636

###### 8.4.2.1[2].[t]*.[r][12].Variable
Q_LINK
- WordTraceId: 14639

###### 8.4.2.1[2].[t]*.[r][12].Length
1
- WordTraceId: 14646

###### 8.4.2.1[2].[t]*.[r][12].Remarks
Marks the balise group as linked (Q_LINK = 1) or unlinked (Q_LINK = 0)
- WordTraceId: 14648

###### 8.4.2.1[2].[t]*.[r][13]
- WordTraceId: 14720

###### 8.4.2.1[2].[t]*.[r][13].Field
- WordTraceId: 14720

###### 8.4.2.1[2].[t]*.[r][13].Variable
Packet 0 (optional)
- WordTraceId: 14721

###### 8.4.2.1[2].[t]*.[r][13].Length
14
- WordTraceId: 14741

###### 8.4.2.1[2].[t]*.[r][13].Remarks
Virtual Balise Cover marker
- WordTraceId: 14744

###### 8.4.2.1[2].[t]*.[r][14]
- WordTraceId: 14773

###### 8.4.2.1[2].[t]*.[r][14].Field
- WordTraceId: 14773

###### 8.4.2.1[2].[t]*.[r][14].Variable
Information
- WordTraceId: 14774

###### 8.4.2.1[2].[t]*.[r][14].Length
Variable
- WordTraceId: 14786

###### 8.4.2.1[2].[t]*.[r][14].Remarks
This information is composed according to the rules applicable for packets.
- WordTraceId: 14795

###### 8.4.2.1[2].[t]*.[r][15]
- WordTraceId: 14872

###### 8.4.2.1[2].[t]*.[r][15].Field
- WordTraceId: 14872

###### 8.4.2.1[2].[t]*.[r][15].Variable
Packet 255
- WordTraceId: 14873

###### 8.4.2.1[2].[t]*.[r][15].Length
8
- WordTraceId: 14884

###### 8.4.2.1[2].[t]*.[r][15].Remarks
Finishing flag of the telegram
- WordTraceId: 14886

###### 8.4.2.1[3]
Number of bits in balise header: 50
- WordTraceId: 14919

###### 8.4.2.2
The user information transmitted by a balise shall contain complete packets, i.e. splitting a packet between two balises is forbidden.
- WordTraceId: 14956

###### 8.4.2.3
When used, the packet 0 shall be transmitted as the first packet of the telegram (i.e. it is appended to the header).
- WordTraceId: 15091

##### 8.4.3
Rules for Euroloop messages
- WordTraceId: 15209

###### 8.4.3.1
The format of the message to be transmitted by each loop is as follows:
- WordTraceId: 15237

###### 8.4.3.1[2]
- WordTraceId: 15310

###### 8.4.3.1[2].[t]*
| General Format of Loop Message |  |  |  |  |
| --- | --- | --- | --- | --- |
| Field No. | VARIABLE | Length ( bits) | Remarks |  |
| [r][3].Field 1 | [r][3].Variable Q_UPDOWN | [r][3].Length 1 | [r][3].Remarks Defines the direction of the information: Down-link message (train to track) (0) Up-link message (track to train) (1) |  |
| [r][4].Field 2 | [r][4].Variable M_VERSION | [r][4].Length 7 | [r][4].Remarks Version of the ERTMS/ETCS system . |  |
| [r][5].Field 3 | [r][5].Variable Q_MEDIA | [r][5].Length 1 | [r][5].Remarks Defines the type of media: Loop (1) |  |
| [r][6].Field 4 | [r][6].Variable NID_C | [r][6].Length 10 | [r][6].Remarks Country or region. |  |
| [r][7].Field 5 | [r][7].Variable NID_LOOP | [r][7].Length 14 | [r][7].Remarks Identity of Euroloop. |  |
| [r][8].Field | [r][8].Variable | [r][8].Length | [r][8].Remarks |  |
| [r][9].Field | [r][9].Variable | [r][9].Length | [r][9].Remarks |  |
| [r][10].Field | [r][10].Variable Information | [r][10].Length Variable | [r][10].Remarks This information is composed according to the rules applicable for packets. |  |
| [r][11].Field | [r][11].Variable Packet 255 | [r][11].Length 8 | [r][11].Remarks Finishing flag of the message |  |
- WordTraceId: 15842

###### 8.4.3.1[2].[t]*.[r][3]
- WordTraceId: 15385

###### 8.4.3.1[2].[t]*.[r][3].Field
1
- WordTraceId: 15385

###### 8.4.3.1[2].[t]*.[r][3].Variable
Q_UPDOWN
- WordTraceId: 15387

###### 8.4.3.1[2].[t]*.[r][3].Length
1
- WordTraceId: 15396

###### 8.4.3.1[2].[t]*.[r][3].Remarks
Defines the direction of the information:
Down-link message (train to track) (0)
Up-link message (track to train) (1)
- WordTraceId: 15398

###### 8.4.3.1[2].[t]*.[r][4]
- WordTraceId: 15519

###### 8.4.3.1[2].[t]*.[r][4].Field
2
- WordTraceId: 15519

###### 8.4.3.1[2].[t]*.[r][4].Variable
M_VERSION
- WordTraceId: 15521

###### 8.4.3.1[2].[t]*.[r][4].Length
7
- WordTraceId: 15531

###### 8.4.3.1[2].[t]*.[r][4].Remarks
Version of the ERTMS/ETCS system .
- PlainText: Version of the ERTMS/ETCS system.
- WordTraceId: 15533

###### 8.4.3.1[2].[t]*.[r][5]
- WordTraceId: 15568

###### 8.4.3.1[2].[t]*.[r][5].Field
3
- WordTraceId: 15568

###### 8.4.3.1[2].[t]*.[r][5].Variable
Q_MEDIA
- WordTraceId: 15570

###### 8.4.3.1[2].[t]*.[r][5].Length
1
- WordTraceId: 15578

###### 8.4.3.1[2].[t]*.[r][5].Remarks
Defines the type of media: Loop (1)
- PlainText: Defines the type of media: Loop   (1)
- WordTraceId: 15580

###### 8.4.3.1[2].[t]*.[r][6]
- WordTraceId: 15619

###### 8.4.3.1[2].[t]*.[r][6].Field
4
- WordTraceId: 15619

###### 8.4.3.1[2].[t]*.[r][6].Variable
NID_C
- WordTraceId: 15621

###### 8.4.3.1[2].[t]*.[r][6].Length
10
- WordTraceId: 15627

###### 8.4.3.1[2].[t]*.[r][6].Remarks
Country or region.
- WordTraceId: 15630

###### 8.4.3.1[2].[t]*.[r][7]
- WordTraceId: 15650

###### 8.4.3.1[2].[t]*.[r][7].Field
5
- WordTraceId: 15650

###### 8.4.3.1[2].[t]*.[r][7].Variable
NID_LOOP
- WordTraceId: 15652

###### 8.4.3.1[2].[t]*.[r][7].Length
14
- WordTraceId: 15661

###### 8.4.3.1[2].[t]*.[r][7].Remarks
Identity of Euroloop.
- WordTraceId: 15664

###### 8.4.3.1[2].[t]*.[r][8]
- WordTraceId: 15687

###### 8.4.3.1[2].[t]*.[r][8].Field
- WordTraceId: 15687

###### 8.4.3.1[2].[t]*.[r][8].Variable
- WordTraceId: 15688

###### 8.4.3.1[2].[t]*.[r][8].Length
- WordTraceId: 15689

###### 8.4.3.1[2].[t]*.[r][8].Remarks
- WordTraceId: 15690

###### 8.4.3.1[2].[t]*.[r][9]
- WordTraceId: 15692

###### 8.4.3.1[2].[t]*.[r][9].Field
- WordTraceId: 15692

###### 8.4.3.1[2].[t]*.[r][9].Variable
- WordTraceId: 15693

###### 8.4.3.1[2].[t]*.[r][9].Length
- WordTraceId: 15694

###### 8.4.3.1[2].[t]*.[r][9].Remarks
- WordTraceId: 15695

###### 8.4.3.1[2].[t]*.[r][10]
- WordTraceId: 15697

###### 8.4.3.1[2].[t]*.[r][10].Field
- WordTraceId: 15697

###### 8.4.3.1[2].[t]*.[r][10].Variable
Information
- WordTraceId: 15698

###### 8.4.3.1[2].[t]*.[r][10].Length
Variable
- WordTraceId: 15710

###### 8.4.3.1[2].[t]*.[r][10].Remarks
This information is composed according to the rules applicable for packets.
- WordTraceId: 15719

###### 8.4.3.1[2].[t]*.[r][11]
- WordTraceId: 15796

###### 8.4.3.1[2].[t]*.[r][11].Field
- WordTraceId: 15796

###### 8.4.3.1[2].[t]*.[r][11].Variable
Packet 255
- WordTraceId: 15797

###### 8.4.3.1[2].[t]*.[r][11].Length
8
- WordTraceId: 15808

###### 8.4.3.1[2].[t]*.[r][11].Remarks
Finishing flag of the message
- WordTraceId: 15810

###### 8.4.3.1[3]
Number of bits in loop header: 33
- WordTraceId: 15842

###### 8.4.3.2
Intentionally deleted.
- WordTraceId: 15877

##### 8.4.4
Rules for Euroradio messages
- WordTraceId: 15901

###### 8.4.4.1
The message identifier is unique (variable NID_MESSAGE).
- WordTraceId: 15930

###### 8.4.4.1.1
All currently not defined message identifiers are reserved for future use and shall be considered as invalid values (i.e. like spare values). E xception: reception of information only differing by Y with regards to the highest system version number X supported by on-board (refer to section 3.17.3.11 b)).
- PlainText: All currently not defined message identifiers are reserved for future use and shall be considered as invalid values (i.e. like spare values). Exception: reception of information only differing by Y with regards to the highest system version number X supported by on-board (refer to section 3.17.3.11 b)).
- WordTraceId: 15987

###### 8.4.4.2
Each message shall indicate its own length through the use of the variable L_MESSAGE.
- WordTraceId: 16292

###### 8.4.4.2.1
If the computed length of the message is not equal to the length given by L_MESSAGE, the entire message shall be rejected.
- WordTraceId: 16378

###### 8.4.4.3
The messages shall be composed of predefined variables and packets.
- WordTraceId: 16501

###### 8.4.4.4
For some messages, it shall be possible to add optional packets at the end of the message.
- WordTraceId: 16569

###### 8.4.4.4.1
The track to train messages possibly including optional packets are listed hereafter:
- WordTraceId: 16660

###### 8.4.4.4.1[2]
- WordTraceId: 16747

###### 8.4.4.4.1[2].[t]*
| [r][1].[c][1] Track to Train message | [r][1].[c][2] Mess. ID | [r][1].[c][3] Optional packets |
| --- | --- | --- |
| [r][2].[c][1] SR Authorisation | [r][2].[c][2] 2 | [r][2].[c][3] 63 |
| [r][3].[c][1] Movement Authority | [r][3].[c][2] 3 | [r][3].[c][3] 21, 27, 49, 80, plus common optional packets |
| [r][4].[c][1] Request To Shorten MA | [r][4].[c][2] 9 | [r][4].[c][3] 49, 80 |
| [r][5].[c][1] General Message | [r][5].[c][2] 24 | [r][5].[c][3] From RBC: 21, 27, plus common optional packets From RIU: 45, 143, 254 |
| [r][6].[c][1] SH authorised | [r][6].[c][2] 28 | [r][6].[c][3] 3, 44, 49 |
| [r][7].[c][1] MA with Shifted Location Reference | [r][7].[c][2] 33 | [r][7].[c][3] 21, 27, 49, 80, plus common optional packets |
| [r][8].[c][1] In f ill MA | [r][8].[c][2] 37 | [r][8].[c][3] 5, 21, 27, 3 9 , 40, 41, 44, 49, 51, 65, 66, 68, 69, 70, 71, 80, 88, 138, 139 |
- WordTraceId: 17214

###### 8.4.4.4.1[2].[t]*.[r][1]
- WordTraceId: 16747

###### 8.4.4.4.1[2].[t]*.[r][1].[c][1]
Track to Train message
- WordTraceId: 16747

###### 8.4.4.4.1[2].[t]*.[r][1].[c][2]
Mess. ID
- WordTraceId: 16770

###### 8.4.4.4.1[2].[t]*.[r][1].[c][3]
Optional packets
- WordTraceId: 16779

###### 8.4.4.4.1[2].[t]*.[r][2]
- WordTraceId: 16797

###### 8.4.4.4.1[2].[t]*.[r][2].[c][1]
SR Authorisation
- WordTraceId: 16797

###### 8.4.4.4.1[2].[t]*.[r][2].[c][2]
2
- WordTraceId: 16814

###### 8.4.4.4.1[2].[t]*.[r][2].[c][3]
63
- WordTraceId: 16816

###### 8.4.4.4.1[2].[t]*.[r][3]
- WordTraceId: 16820

###### 8.4.4.4.1[2].[t]*.[r][3].[c][1]
Movement Authority
- WordTraceId: 16820

###### 8.4.4.4.1[2].[t]*.[r][3].[c][2]
3
- WordTraceId: 16839

###### 8.4.4.4.1[2].[t]*.[r][3].[c][3]
21, 27, 49, 80, plus common optional packets
- WordTraceId: 16841

###### 8.4.4.4.1[2].[t]*.[r][4]
- WordTraceId: 16887

###### 8.4.4.4.1[2].[t]*.[r][4].[c][1]
Request To Shorten MA
- WordTraceId: 16887

###### 8.4.4.4.1[2].[t]*.[r][4].[c][2]
9
- WordTraceId: 16909

###### 8.4.4.4.1[2].[t]*.[r][4].[c][3]
49, 80
- WordTraceId: 16911

###### 8.4.4.4.1[2].[t]*.[r][5]
- WordTraceId: 16919

###### 8.4.4.4.1[2].[t]*.[r][5].[c][1]
General Message
- WordTraceId: 16919

###### 8.4.4.4.1[2].[t]*.[r][5].[c][2]
24
- WordTraceId: 16935

###### 8.4.4.4.1[2].[t]*.[r][5].[c][3]
From RBC: 21, 27, plus common optional packets
From RIU: 45, 143, 254
- WordTraceId: 16938

###### 8.4.4.4.1[2].[t]*.[r][6]
- WordTraceId: 17009

###### 8.4.4.4.1[2].[t]*.[r][6].[c][1]
SH authorised
- WordTraceId: 17009

###### 8.4.4.4.1[2].[t]*.[r][6].[c][2]
28
- WordTraceId: 17023

###### 8.4.4.4.1[2].[t]*.[r][6].[c][3]
3, 44, 49
- WordTraceId: 17026

###### 8.4.4.4.1[2].[t]*.[r][7]
- WordTraceId: 17037

###### 8.4.4.4.1[2].[t]*.[r][7].[c][1]
MA with Shifted Location Reference
- WordTraceId: 17037

###### 8.4.4.4.1[2].[t]*.[r][7].[c][2]
33
- WordTraceId: 17072

###### 8.4.4.4.1[2].[t]*.[r][7].[c][3]
21, 27, 49, 80, plus common optional packets
- WordTraceId: 17075

###### 8.4.4.4.1[2].[t]*.[r][8]
- WordTraceId: 17122

###### 8.4.4.4.1[2].[t]*.[r][8].[c][1]
In f ill MA
- PlainText: Infill MA
- WordTraceId: 17122

###### 8.4.4.4.1[2].[t]*.[r][8].[c][2]
37
- WordTraceId: 17132

###### 8.4.4.4.1[2].[t]*.[r][8].[c][3]
5, 21, 27, 3 9 , 40, 41, 44, 49, 51, 65, 66, 68, 69, 70, 71, 80, 88, 138, 139
- PlainText: 5, 21, 27, 39, 40, 41, 44, 49, 51, 65, 66, 68, 69, 70, 71, 80, 88, 138, 139
- WordTraceId: 17135

###### 8.4.4.4.1[2].1
The common optional packets are the following ones:
- ListNumberText: 8.4.4.4.1.1
- WordTraceId: 17214

###### 8.4.4.4.1[2].1[2]
- WordTraceId: 17267

###### 8.4.4.4.1[2].1[2].[t]*
| [r][1].[c][1] Common optional packets |
| --- |
| [r][2].[c][1] 3, 5, 39, 40, 51, 41, 42, 44, 45, 52, 57, 58, 64, 65, 66, 68, 69, 70, 71, 72, 76, 79, 88, 131, 138, 139, 140 |
- WordTraceId: 17403

###### 8.4.4.4.1[2].1[2].[t]*.[r][1]
- WordTraceId: 17267

###### 8.4.4.4.1[2].1[2].[t]*.[r][1].[c][1]
Common optional packets
- WordTraceId: 17267

###### 8.4.4.4.1[2].1[2].[t]*.[r][2]
- WordTraceId: 17292

###### 8.4.4.4.1[2].1[2].[t]*.[r][2].[c][1]
3, 5, 39, 40, 51, 41, 42, 44, 45, 52, 57, 58, 64, 65, 66, 68, 69, 70, 71, 72, 76, 79, 88, 131, 138, 139, 140
- WordTraceId: 17292

###### 8.4.4.4.2
The train to track message 136 (Train Position Report) and 157 (SoM Position Report) may optionally include the following packets:
- WordTraceId: 17403

###### 8.4.4.4.2.a
Packet 4 (Error Reporting),
- ListNumberText: a)
- WordTraceId: 17534

###### 8.4.4.4.2.b
Packet 5 (Train running number),
- ListNumberText: b)
- WordTraceId: 17562

###### 8.4.4.4.2.c
Packet 44 (Data used by applications outside the ERTMS/ETCS system).
- ListNumberText: c)
- WordTraceId: 17595

###### 8.4.4.4.3
The train to track message 159 (Session Established) may optionally include the following packets:
- WordTraceId: 17664

###### 8.4.4.4.3.a
Packet 3 (Onboard Telephone Numbers)
- ListNumberText: a)
- WordTraceId: 17763

###### 8.4.4.4.4
The train to track message 132 (MA request) may optionally include the following packet:
- WordTraceId: 17800

###### 8.4.4.4.4[2]
a) Packet 9 (Level 2/3 transition information)
- WordTraceId: 17889

###### 8.4.4.5
If needed to obtain an integer number of bytes, padding shall be added at the end of the message.
- WordTraceId: 17936

###### 8.4.4.6
Standard format of a radio message from track to train :
- WordTraceId: 18035

###### 8.4.4.6.1
Format:
- WordTraceId: 18092

###### 8.4.4.6.1[2]
- WordTraceId: 18101

###### 8.4.4.6.1[2].[t]*
| Field No. | VARIABLE | Remarks |
| --- | --- | --- |
| [r][2].Field {1} | [r][2].Variable NID_MESSAGE | [r][2].Remarks Message Identification Number |
| [r][3].Field {2} | [r][3].Variable L_MESSAGE | [r][3].Remarks Message length including everything ( from field 1 to padding inclusive ). |
| [r][4].Field {3} | [r][4].Variable T_TRAIN | [r][4].Remarks Time Stamp from RBC ( see sections 3.16.3.2 & 3.16.3.3 ). |
| [r][5].Field {4} | [r][5].Variable M_ACK | [r][5].Remarks Indicates whether the message must be acknowledged (or not) by the on-board equipment (message n° 146). |
| [r][6].Field {5} | [r][6].Variable NID_LRBG | [r][6].Remarks Identification Number of LRBG. |
| … | [r][7].Variable variables as required by NID_MESSAGE | [r][7].Remarks If needed for this message. Used when sending variables which are not included in a packet. |
| … | [r][8].Variable packets as required by NID_MESSAGE | [r][8].Remarks If needed for this message. |
|  | [r][9].Variable Optional packets | [r][9].Remarks Refer to section 8.4.4.4 of this document. |
|  | [r][10].Variable Padding | [r][10].Remarks If required. |
- WordTraceId: 18764

###### 8.4.4.6.1[2].[t]*.[r][2]
- WordTraceId: 18129

###### 8.4.4.6.1[2].[t]*.[r][2].Field
{1}
- PlainText: 1
- WordTraceId: 18129

###### 8.4.4.6.1[2].[t]*.[r][2].Variable
NID_MESSAGE
- WordTraceId: 18130

###### 8.4.4.6.1[2].[t]*.[r][2].Remarks
Message Identification Number
- WordTraceId: 18142

###### 8.4.4.6.1[2].[t]*.[r][3]
- WordTraceId: 18173

###### 8.4.4.6.1[2].[t]*.[r][3].Field
{2}
- PlainText: 2
- WordTraceId: 18173

###### 8.4.4.6.1[2].[t]*.[r][3].Variable
L_MESSAGE
- WordTraceId: 18174

###### 8.4.4.6.1[2].[t]*.[r][3].Remarks
Message length including everything ( from field 1 to padding inclusive ).
- PlainText: Message length including everything (from field 1 to padding inclusive).
- WordTraceId: 18184

###### 8.4.4.6.1[2].[t]*.[r][4]
- WordTraceId: 18258

###### 8.4.4.6.1[2].[t]*.[r][4].Field
{3}
- PlainText: 3
- WordTraceId: 18258

###### 8.4.4.6.1[2].[t]*.[r][4].Variable
T_TRAIN
- WordTraceId: 18259

###### 8.4.4.6.1[2].[t]*.[r][4].Remarks
Time Stamp from RBC ( see sections 3.16.3.2 & 3.16.3.3 ).
- PlainText: Time Stamp from RBC (see sections 3.16.3.2 & 3.16.3.3).
- WordTraceId: 18267

###### 8.4.4.6.1[2].[t]*.[r][5]
- WordTraceId: 18324

###### 8.4.4.6.1[2].[t]*.[r][5].Field
{4}
- PlainText: 4
- WordTraceId: 18324

###### 8.4.4.6.1[2].[t]*.[r][5].Variable
M_ACK
- WordTraceId: 18325

###### 8.4.4.6.1[2].[t]*.[r][5].Remarks
Indicates whether the message must be acknowledged (or not) by the on-board equipment (message n° 146).
- WordTraceId: 18331

###### 8.4.4.6.1[2].[t]*.[r][6]
- WordTraceId: 18436

###### 8.4.4.6.1[2].[t]*.[r][6].Field
{5}
- PlainText: 5
- WordTraceId: 18436

###### 8.4.4.6.1[2].[t]*.[r][6].Variable
NID_LRBG
- WordTraceId: 18437

###### 8.4.4.6.1[2].[t]*.[r][6].Remarks
Identification Number of LRBG.
- WordTraceId: 18446

###### 8.4.4.6.1[2].[t]*.[r][7]
- WordTraceId: 18478

###### 8.4.4.6.1[2].[t]*.[r][7].Variable
variables as required by NID_MESSAGE
- WordTraceId: 18480

###### 8.4.4.6.1[2].[t]*.[r][7].Remarks
If needed for this message. Used when sending variables which are not included in a packet.
- WordTraceId: 18517

###### 8.4.4.6.1[2].[t]*.[r][8]
- WordTraceId: 18611

###### 8.4.4.6.1[2].[t]*.[r][8].Variable
packets as required by NID_MESSAGE
- WordTraceId: 18613

###### 8.4.4.6.1[2].[t]*.[r][8].Remarks
If needed for this message.
- WordTraceId: 18648

###### 8.4.4.6.1[2].[t]*.[r][9]
- WordTraceId: 18678

###### 8.4.4.6.1[2].[t]*.[r][9].Variable
Optional packets
- WordTraceId: 18679

###### 8.4.4.6.1[2].[t]*.[r][9].Remarks
Refer to section 8.4.4.4 of this document.
- WordTraceId: 18696

###### 8.4.4.6.1[2].[t]*.[r][10]
- WordTraceId: 18740

###### 8.4.4.6.1[2].[t]*.[r][10].Variable
Padding
- WordTraceId: 18741

###### 8.4.4.6.1[2].[t]*.[r][10].Remarks
If required.
- WordTraceId: 18749

###### 8.4.4.6.2
Note: In section 8.7 giving the contents of the messages, the padding information is intentionally omitted.
- WordTraceId: 18765

###### 8.4.4.6.3
The track to train message 39 (Acknowledgement of termination of a communication session) shall include the variable M_ACK set to 0. Justification: see 3.5.5.3.
- WordTraceId: 18873

###### 8.4.4.7
Standard format of a radio message from train to track:
- WordTraceId: 19034

###### 8.4.4.7.1
Format:
- WordTraceId: 19090

###### 8.4.4.7.1[2]
- WordTraceId: 19099

###### 8.4.4.7.1[2].[t]*
| Field No. | VARIABLE | Remarks |
| --- | --- | --- |
| [r][2].Field {1} | [r][2].Variable NID_MESSAGE | [r][2].Remarks Message Identification Number |
| [r][3].Field {2} | [r][3].Variable L_MESSAGE | [r][3].Remarks Message length including everything ( from field 1 to padding inclusive ). |
| [r][4].Field {3} | [r][4].Variable T_TRAIN | [r][4].Remarks Time Stamp from Train (see chapter 3 – Data Consistency). |
| [r][5].Field {4} | [r][5].Variable NID_ENGINE | [r][5].Remarks Identity of the train. |
| [r][6].Field {5} | [r][6].Variable variables as required by NID_MESSAGE | [r][6].Remarks If needed for this message. Used when sending variables which are not included in a packet. |
| [r][7].Field {6} | [r][7].Variable Packet 0 or 1 | [r][7].Remarks Train-to-track packet type 0 – Position report, or packet type 1 - Position report based on two balise groups. Not included in messages 146, 154, 155, 156 and 159. |
| [r][8].Field {7} | [r][8].Variable Other Packets as required by NID_MESSAGE | [r][8].Remarks (only for message 129) |
| [r][9].Field {8} | [r][9].Variable Optional packets |  |
|  | [r][10].Variable Padding | [r][10].Remarks If required. |
- WordTraceId: 19782

###### 8.4.4.7.1[2].[t]*.[r][2]
- WordTraceId: 19127

###### 8.4.4.7.1[2].[t]*.[r][2].Field
{1}
- PlainText: 1
- WordTraceId: 19127

###### 8.4.4.7.1[2].[t]*.[r][2].Variable
NID_MESSAGE
- WordTraceId: 19128

###### 8.4.4.7.1[2].[t]*.[r][2].Remarks
Message Identification Number
- WordTraceId: 19140

###### 8.4.4.7.1[2].[t]*.[r][3]
- WordTraceId: 19171

###### 8.4.4.7.1[2].[t]*.[r][3].Field
{2}
- PlainText: 2
- WordTraceId: 19171

###### 8.4.4.7.1[2].[t]*.[r][3].Variable
L_MESSAGE
- WordTraceId: 19172

###### 8.4.4.7.1[2].[t]*.[r][3].Remarks
Message length including everything ( from field 1 to padding inclusive ).
- PlainText: Message length including everything (from field 1 to padding inclusive).
- WordTraceId: 19182

###### 8.4.4.7.1[2].[t]*.[r][4]
- WordTraceId: 19257

###### 8.4.4.7.1[2].[t]*.[r][4].Field
{3}
- PlainText: 3
- WordTraceId: 19257

###### 8.4.4.7.1[2].[t]*.[r][4].Variable
T_TRAIN
- WordTraceId: 19258

###### 8.4.4.7.1[2].[t]*.[r][4].Remarks
Time Stamp from Train (see chapter 3 – Data Consistency).
- WordTraceId: 19266

###### 8.4.4.7.1[2].[t]*.[r][5]
- WordTraceId: 19325

###### 8.4.4.7.1[2].[t]*.[r][5].Field
{4}
- PlainText: 4
- WordTraceId: 19325

###### 8.4.4.7.1[2].[t]*.[r][5].Variable
NID_ENGINE
- WordTraceId: 19326

###### 8.4.4.7.1[2].[t]*.[r][5].Remarks
Identity of the train.
- WordTraceId: 19337

###### 8.4.4.7.1[2].[t]*.[r][6]
- WordTraceId: 19361

###### 8.4.4.7.1[2].[t]*.[r][6].Field
{5}
- PlainText: 5
- WordTraceId: 19361

###### 8.4.4.7.1[2].[t]*.[r][6].Variable
variables as required by NID_MESSAGE
- WordTraceId: 19362

###### 8.4.4.7.1[2].[t]*.[r][6].Remarks
If needed for this message. Used when sending variables which are not included in a packet.
- WordTraceId: 19399

###### 8.4.4.7.1[2].[t]*.[r][7]
- WordTraceId: 19492

###### 8.4.4.7.1[2].[t]*.[r][7].Field
{6}
- PlainText: 6
- WordTraceId: 19492

###### 8.4.4.7.1[2].[t]*.[r][7].Variable
Packet 0 or 1
- WordTraceId: 19493

###### 8.4.4.7.1[2].[t]*.[r][7].Remarks
Train-to-track packet type 0 – Position report, or packet type 1 - Position report based on two balise groups. Not included in messages 146, 154, 155, 156 and 159.
- WordTraceId: 19507

###### 8.4.4.7.1[2].[t]*.[r][8]
- WordTraceId: 19672

###### 8.4.4.7.1[2].[t]*.[r][8].Field
{7}
- PlainText: 7
- WordTraceId: 19672

###### 8.4.4.7.1[2].[t]*.[r][8].Variable
Other Packets as required by NID_MESSAGE
- WordTraceId: 19673

###### 8.4.4.7.1[2].[t]*.[r][8].Remarks
(only for message 129)
- WordTraceId: 19714

###### 8.4.4.7.1[2].[t]*.[r][9]
- WordTraceId: 19738

###### 8.4.4.7.1[2].[t]*.[r][9].Field
{8}
- PlainText: 8
- WordTraceId: 19738

###### 8.4.4.7.1[2].[t]*.[r][9].Variable
Optional packets
- WordTraceId: 19739

###### 8.4.4.7.1[2].[t]*.[r][10]
- WordTraceId: 19758

###### 8.4.4.7.1[2].[t]*.[r][10].Variable
Padding
- WordTraceId: 19759

###### 8.4.4.7.1[2].[t]*.[r][10].Remarks
If required.
- WordTraceId: 19767

###### 8.4.4.7.2
Exception: The position report (packet 0 or packet 1) shall not be included in the following messages:
- WordTraceId: 19782

###### 8.4.4.7.2.a
Message 146 (Acknowledgement),
- ListNumberText: a)
- WordTraceId: 19886

###### 8.4.4.7.2.b
Message 154 (No compatible version supported ),
- ListNumberText: b)
- PlainText: Message 154 (No compatible version supported),
- WordTraceId: 19917

###### 8.4.4.7.2.c
Message 155 (Initiation of a communication session),
- ListNumberText: c)
- WordTraceId: 19964

###### 8.4.4.7.2.d
Message 156 (Termination of a communication session),
- ListNumberText: d)
- WordTraceId: 20017

###### 8.4.4.7.2.e
Intentionally deleted
- ListNumberText: e)
- WordTraceId: 20071

###### 8.4.4.7.2.f
Message 159 (Session Established).
- ListNumberText: f)
- WordTraceId: 20093

###### 8.4.4.7.3
Note: In section 8.6 giving the contents of the messages, the padding information is intentionally omitted.
- WordTraceId: 20128

#### 8.5
List of radio Messages
- WordTraceId: 20238

##### 8.5.1
Introduction
- WordTraceId: 20261

###### 8.5.1.1
This section identifies the radio messages with corresponding Message Identifier (“Mes. Id.”) and Message Name. It also gives a list of the version-invariant messages.
- WordTraceId: 20274

###### 8.5.1.2
“Type” defines whether a message is to be sent as normal priority (N) or as high priority data (E), as defined in Euroradio specifications.
- WordTraceId: 20442

##### 8.5.2
Train to Track radio messages
- WordTraceId: 20582

##### 8.5.2[2]
- WordTraceId: 20613

###### 8.5.2[2].[t]*
| Mes. Id. | Message Name | Type | Invariant | Transmitted to |
| --- | --- | --- | --- | --- |
| [r][2].ID 129 | [r][2].Name Validated Train Data | [r][2].Type N | [r][2].Inv No | [r][2].Medium RBC |
| [r][3].ID 130 | [r][3].Name Request for Shunting | [r][3].Type N | [r][3].Inv No | [r][3].Medium RBC |
| [r][4].ID 132 | [r][4].Name MA Request | [r][4].Type N | [r][4].Inv No | [r][4].Medium RBC |
| [r][5].ID 136 | [r][5].Name Train Position Report | [r][5].Type N | [r][5].Inv No | [r][5].Medium RBC, RIU |
| [r][6].ID 137 | [r][6].Name Request to shorten MA is granted | [r][6].Type N | [r][6].Inv No | [r][6].Medium RBC |
| [r][7].ID 138 | [r][7].Name Request to shorten MA is rejected | [r][7].Type N | [r][7].Inv No | [r][7].Medium RBC |
| [r][8].ID 146 | [r][8].Name Acknowledgement | [r][8].Type N | [r][8].Inv No | [r][8].Medium RBC, RIU |
| [r][9].ID 147 | [r][9].Name Acknowledgement of Emergency Stop | [r][9].Type N | [r][9].Inv No | [r][9].Medium RBC |
| [r][10].ID 149 | [r][10].Name Track Ahead Free Granted | [r][10].Type N | [r][10].Inv No | [r][10].Medium RBC |
| [r][11].ID 150 | [r][11].Name End of Mission | [r][11].Type N | [r][11].Inv No | [r][11].Medium RBC |
| [r][12].ID 153 | [r][12].Name Radio infill request | [r][12].Type N | [r][12].Inv No | [r][12].Medium RIU |
| [r][13].ID 154 | [r][13].Name No compatible version supported | [r][13].Type N | [r][13].Inv Yes | [r][13].Medium RBC, RIU |
| [r][14].ID 155 | [r][14].Name Initiation of a communication session | [r][14].Type N | [r][14].Inv Yes | [r][14].Medium RBC, RIU |
| [r][15].ID 156 | [r][15].Name Termination of a communication session | [r][15].Type N | [r][15].Inv Yes | [r][15].Medium RBC, RIU |
| [r][16].ID 157 | [r][16].Name SoM Position Report | [r][16].Type N | [r][16].Inv No | [r][16].Medium RBC |
| [r][17].ID 158 | [r][17].Name Text message acknowledged by driver | [r][17].Type N | [r][17].Inv No | [r][17].Medium RBC |
| [r][18].ID 159 | [r][18].Name Session Established | [r][18].Type N | [r][18].Inv No | [r][18].Medium RBC, RIU |
- WordTraceId: 21376

###### 8.5.2[2].[t]*.[r][2]
- WordTraceId: 20666

###### 8.5.2[2].[t]*.[r][2].ID
129
- WordTraceId: 20666

###### 8.5.2[2].[t]*.[r][2].Name
Validated Train Data
- WordTraceId: 20670

###### 8.5.2[2].[t]*.[r][2].Type
N
- WordTraceId: 20691

###### 8.5.2[2].[t]*.[r][2].Inv
No
- WordTraceId: 20693

###### 8.5.2[2].[t]*.[r][2].Medium
RBC
- WordTraceId: 20696

###### 8.5.2[2].[t]*.[r][3]
- WordTraceId: 20701

###### 8.5.2[2].[t]*.[r][3].ID
130
- WordTraceId: 20701

###### 8.5.2[2].[t]*.[r][3].Name
Request for Shunting
- WordTraceId: 20705

###### 8.5.2[2].[t]*.[r][3].Type
N
- WordTraceId: 20726

###### 8.5.2[2].[t]*.[r][3].Inv
No
- WordTraceId: 20728

###### 8.5.2[2].[t]*.[r][3].Medium
RBC
- WordTraceId: 20731

###### 8.5.2[2].[t]*.[r][4]
- WordTraceId: 20736

###### 8.5.2[2].[t]*.[r][4].ID
132
- WordTraceId: 20736

###### 8.5.2[2].[t]*.[r][4].Name
MA Request
- WordTraceId: 20740

###### 8.5.2[2].[t]*.[r][4].Type
N
- WordTraceId: 20751

###### 8.5.2[2].[t]*.[r][4].Inv
No
- WordTraceId: 20753

###### 8.5.2[2].[t]*.[r][4].Medium
RBC
- WordTraceId: 20756

###### 8.5.2[2].[t]*.[r][5]
- WordTraceId: 20761

###### 8.5.2[2].[t]*.[r][5].ID
136
- WordTraceId: 20761

###### 8.5.2[2].[t]*.[r][5].Name
Train Position Report
- WordTraceId: 20765

###### 8.5.2[2].[t]*.[r][5].Type
N
- WordTraceId: 20787

###### 8.5.2[2].[t]*.[r][5].Inv
No
- WordTraceId: 20789

###### 8.5.2[2].[t]*.[r][5].Medium
RBC, RIU
- WordTraceId: 20792

###### 8.5.2[2].[t]*.[r][6]
- WordTraceId: 20802

###### 8.5.2[2].[t]*.[r][6].ID
137
- WordTraceId: 20802

###### 8.5.2[2].[t]*.[r][6].Name
Request to shorten MA is granted
- WordTraceId: 20806

###### 8.5.2[2].[t]*.[r][6].Type
N
- WordTraceId: 20839

###### 8.5.2[2].[t]*.[r][6].Inv
No
- WordTraceId: 20841

###### 8.5.2[2].[t]*.[r][6].Medium
RBC
- WordTraceId: 20844

###### 8.5.2[2].[t]*.[r][7]
- WordTraceId: 20849

###### 8.5.2[2].[t]*.[r][7].ID
138
- WordTraceId: 20849

###### 8.5.2[2].[t]*.[r][7].Name
Request to shorten MA is rejected
- WordTraceId: 20853

###### 8.5.2[2].[t]*.[r][7].Type
N
- WordTraceId: 20887

###### 8.5.2[2].[t]*.[r][7].Inv
No
- WordTraceId: 20889

###### 8.5.2[2].[t]*.[r][7].Medium
RBC
- WordTraceId: 20892

###### 8.5.2[2].[t]*.[r][8]
- WordTraceId: 20897

###### 8.5.2[2].[t]*.[r][8].ID
146
- WordTraceId: 20897

###### 8.5.2[2].[t]*.[r][8].Name
Acknowledgement
- WordTraceId: 20901

###### 8.5.2[2].[t]*.[r][8].Type
N
- WordTraceId: 20917

###### 8.5.2[2].[t]*.[r][8].Inv
No
- WordTraceId: 20919

###### 8.5.2[2].[t]*.[r][8].Medium
RBC, RIU
- WordTraceId: 20922

###### 8.5.2[2].[t]*.[r][9]
- WordTraceId: 20932

###### 8.5.2[2].[t]*.[r][9].ID
147
- WordTraceId: 20932

###### 8.5.2[2].[t]*.[r][9].Name
Acknowledgement of Emergency Stop
- WordTraceId: 20936

###### 8.5.2[2].[t]*.[r][9].Type
N
- WordTraceId: 20970

###### 8.5.2[2].[t]*.[r][9].Inv
No
- WordTraceId: 20972

###### 8.5.2[2].[t]*.[r][9].Medium
RBC
- WordTraceId: 20975

###### 8.5.2[2].[t]*.[r][10]
- WordTraceId: 20980

###### 8.5.2[2].[t]*.[r][10].ID
149
- WordTraceId: 20980

###### 8.5.2[2].[t]*.[r][10].Name
Track Ahead Free Granted
- WordTraceId: 20984

###### 8.5.2[2].[t]*.[r][10].Type
N
- WordTraceId: 21009

###### 8.5.2[2].[t]*.[r][10].Inv
No
- WordTraceId: 21011

###### 8.5.2[2].[t]*.[r][10].Medium
RBC
- WordTraceId: 21014

###### 8.5.2[2].[t]*.[r][11]
- WordTraceId: 21019

###### 8.5.2[2].[t]*.[r][11].ID
150
- WordTraceId: 21019

###### 8.5.2[2].[t]*.[r][11].Name
End of Mission
- WordTraceId: 21023

###### 8.5.2[2].[t]*.[r][11].Type
N
- WordTraceId: 21038

###### 8.5.2[2].[t]*.[r][11].Inv
No
- WordTraceId: 21040

###### 8.5.2[2].[t]*.[r][11].Medium
RBC
- WordTraceId: 21043

###### 8.5.2[2].[t]*.[r][12]
- WordTraceId: 21048

###### 8.5.2[2].[t]*.[r][12].ID
153
- WordTraceId: 21048

###### 8.5.2[2].[t]*.[r][12].Name
Radio infill request
- WordTraceId: 21052

###### 8.5.2[2].[t]*.[r][12].Type
N
- WordTraceId: 21073

###### 8.5.2[2].[t]*.[r][12].Inv
No
- WordTraceId: 21075

###### 8.5.2[2].[t]*.[r][12].Medium
RIU
- WordTraceId: 21078

###### 8.5.2[2].[t]*.[r][13]
- WordTraceId: 21083

###### 8.5.2[2].[t]*.[r][13].ID
154
- WordTraceId: 21083

###### 8.5.2[2].[t]*.[r][13].Name
No compatible version supported
- WordTraceId: 21087

###### 8.5.2[2].[t]*.[r][13].Type
N
- WordTraceId: 21119

###### 8.5.2[2].[t]*.[r][13].Inv
Yes
- WordTraceId: 21121

###### 8.5.2[2].[t]*.[r][13].Medium
RBC, RIU
- WordTraceId: 21125

###### 8.5.2[2].[t]*.[r][14]
- WordTraceId: 21135

###### 8.5.2[2].[t]*.[r][14].ID
155
- WordTraceId: 21135

###### 8.5.2[2].[t]*.[r][14].Name
Initiation of a communication session
- WordTraceId: 21139

###### 8.5.2[2].[t]*.[r][14].Type
N
- WordTraceId: 21177

###### 8.5.2[2].[t]*.[r][14].Inv
Yes
- WordTraceId: 21179

###### 8.5.2[2].[t]*.[r][14].Medium
RBC, RIU
- WordTraceId: 21183

###### 8.5.2[2].[t]*.[r][15]
- WordTraceId: 21193

###### 8.5.2[2].[t]*.[r][15].ID
156
- WordTraceId: 21193

###### 8.5.2[2].[t]*.[r][15].Name
Termination of a communication session
- WordTraceId: 21197

###### 8.5.2[2].[t]*.[r][15].Type
N
- WordTraceId: 21236

###### 8.5.2[2].[t]*.[r][15].Inv
Yes
- WordTraceId: 21238

###### 8.5.2[2].[t]*.[r][15].Medium
RBC, RIU
- WordTraceId: 21242

###### 8.5.2[2].[t]*.[r][16]
- WordTraceId: 21252

###### 8.5.2[2].[t]*.[r][16].ID
157
- WordTraceId: 21252

###### 8.5.2[2].[t]*.[r][16].Name
SoM Position Report
- WordTraceId: 21256

###### 8.5.2[2].[t]*.[r][16].Type
N
- WordTraceId: 21276

###### 8.5.2[2].[t]*.[r][16].Inv
No
- WordTraceId: 21278

###### 8.5.2[2].[t]*.[r][16].Medium
RBC
- WordTraceId: 21281

###### 8.5.2[2].[t]*.[r][17]
- WordTraceId: 21286

###### 8.5.2[2].[t]*.[r][17].ID
158
- WordTraceId: 21286

###### 8.5.2[2].[t]*.[r][17].Name
Text message acknowledged by driver
- WordTraceId: 21290

###### 8.5.2[2].[t]*.[r][17].Type
N
- WordTraceId: 21326

###### 8.5.2[2].[t]*.[r][17].Inv
No
- WordTraceId: 21328

###### 8.5.2[2].[t]*.[r][17].Medium
RBC
- WordTraceId: 21331

###### 8.5.2[2].[t]*.[r][18]
- WordTraceId: 21336

###### 8.5.2[2].[t]*.[r][18].ID
159
- WordTraceId: 21336

###### 8.5.2[2].[t]*.[r][18].Name
Session Established
- WordTraceId: 21340

###### 8.5.2[2].[t]*.[r][18].Type
N
- WordTraceId: 21360

###### 8.5.2[2].[t]*.[r][18].Inv
No
- WordTraceId: 21362

###### 8.5.2[2].[t]*.[r][18].Medium
RBC, RIU
- WordTraceId: 21365

##### 8.5.3
Track to Train radio messages
- WordTraceId: 21377

##### 8.5.3[2]
- WordTraceId: 21408

###### 8.5.3[2].[t]*
| Mes. Id. | Message Name | Type | Invariant | Transmitted by |
| --- | --- | --- | --- | --- |
| [r][2].ID 2 | [r][2].Name SR Authorisation | [r][2].Type N | [r][2].Inv No | [r][2].Medium RBC |
| [r][3].ID 3 | [r][3].Name Movement Authority | [r][3].Type N | [r][3].Inv No | [r][3].Medium RBC |
| [r][4].ID 6 | [r][4].Name Recognition of exit from TRIP mode | [r][4].Type N | [r][4].Inv No | [r][4].Medium RBC |
| [r][5].ID 8 | [r][5].Name Acknowledgement of Train Data | [r][5].Type N | [r][5].Inv No | [r][5].Medium RBC |
| [r][6].ID 9 | [r][6].Name Request to Shorten MA | [r][6].Type N | [r][6].Inv No | [r][6].Medium RBC |
| [r][7].ID 15 | [r][7].Name Conditional Emergency Stop | [r][7].Type E or N | [r][7].Inv No | [r][7].Medium RBC |
| [r][8].ID 16 | [r][8].Name Unconditional Emergency Stop | [r][8].Type E or N | [r][8].Inv No | [r][8].Medium RBC |
| [r][9].ID 18 | [r][9].Name Revocation of Emergency Stop | [r][9].Type N | [r][9].Inv No | [r][9].Medium RBC |
| [r][10].ID 24 | [r][10].Name General message | [r][10].Type N | [r][10].Inv No | [r][10].Medium RBC, RIU |
| [r][11].ID 27 | [r][11].Name SH Refused | [r][11].Type N | [r][11].Inv No | [r][11].Medium RBC |
| [r][12].ID 28 | [r][12].Name SH Authorised | [r][12].Type N | [r][12].Inv No | [r][12].Medium RBC |
| [r][13].ID 33 | [r][13].Name MA with Shifted Location Reference | [r][13].Type N | [r][13].Inv No | [r][13].Medium RBC |
| [r][14].ID 34 | [r][14].Name Track Ahead Free Request | [r][14].Type N | [r][14].Inv No | [r][14].Medium RBC |
| [r][15].ID 37 | [r][15].Name Infill MA | [r][15].Type N | [r][15].Inv No | [r][15].Medium RIU |
| [r][16].ID 40 | [r][16].Name Train Rejected | [r][16].Type N | [r][16].Inv No | [r][16].Medium RBC |
| [r][17].ID 32 | [r][17].Name RBC/RIU System Version | [r][17].Type N | [r][17].Inv Yes | [r][17].Medium RBC, RIU |
| [r][18].ID 38 | [r][18].Name Initiation of a communication session | [r][18].Type N | [r][18].Inv Yes | [r][18].Medium RBC |
| [r][19].ID 39 | [r][19].Name Acknowledgement of termination of a communication session | [r][19].Type N | [r][19].Inv Yes | [r][19].Medium RBC, RIU |
| [r][20].ID 41 | [r][20].Name Train Accepted | [r][20].Type N | [r][20].Inv No | [r][20].Medium RBC |
| [r][21].ID 43 | [r][21].Name SoM position report confirmed by RBC | [r][21].Type N | [r][21].Inv No | [r][21].Medium RBC |
| [r][22].ID 45 | [r][22].Name Assignment of coordinate system | [r][22].Type N | [r][22].Inv No | [r][22].Medium RBC |
- WordTraceId: 22294

###### 8.5.3[2].[t]*.[r][2]
- WordTraceId: 21461

###### 8.5.3[2].[t]*.[r][2].ID
2
- WordTraceId: 21461

###### 8.5.3[2].[t]*.[r][2].Name
SR Authorisation
- WordTraceId: 21463

###### 8.5.3[2].[t]*.[r][2].Type
N
- WordTraceId: 21480

###### 8.5.3[2].[t]*.[r][2].Inv
No
- WordTraceId: 21482

###### 8.5.3[2].[t]*.[r][2].Medium
RBC
- WordTraceId: 21485

###### 8.5.3[2].[t]*.[r][3]
- WordTraceId: 21490

###### 8.5.3[2].[t]*.[r][3].ID
3
- WordTraceId: 21490

###### 8.5.3[2].[t]*.[r][3].Name
Movement Authority
- WordTraceId: 21492

###### 8.5.3[2].[t]*.[r][3].Type
N
- WordTraceId: 21511

###### 8.5.3[2].[t]*.[r][3].Inv
No
- WordTraceId: 21513

###### 8.5.3[2].[t]*.[r][3].Medium
RBC
- WordTraceId: 21516

###### 8.5.3[2].[t]*.[r][4]
- WordTraceId: 21521

###### 8.5.3[2].[t]*.[r][4].ID
6
- WordTraceId: 21521

###### 8.5.3[2].[t]*.[r][4].Name
Recognition of exit from TRIP mode
- WordTraceId: 21523

###### 8.5.3[2].[t]*.[r][4].Type
N
- WordTraceId: 21558

###### 8.5.3[2].[t]*.[r][4].Inv
No
- WordTraceId: 21560

###### 8.5.3[2].[t]*.[r][4].Medium
RBC
- WordTraceId: 21563

###### 8.5.3[2].[t]*.[r][5]
- WordTraceId: 21568

###### 8.5.3[2].[t]*.[r][5].ID
8
- WordTraceId: 21568

###### 8.5.3[2].[t]*.[r][5].Name
Acknowledgement of Train Data
- WordTraceId: 21570

###### 8.5.3[2].[t]*.[r][5].Type
N
- WordTraceId: 21600

###### 8.5.3[2].[t]*.[r][5].Inv
No
- WordTraceId: 21602

###### 8.5.3[2].[t]*.[r][5].Medium
RBC
- WordTraceId: 21605

###### 8.5.3[2].[t]*.[r][6]
- WordTraceId: 21610

###### 8.5.3[2].[t]*.[r][6].ID
9
- WordTraceId: 21610

###### 8.5.3[2].[t]*.[r][6].Name
Request to Shorten MA
- WordTraceId: 21612

###### 8.5.3[2].[t]*.[r][6].Type
N
- WordTraceId: 21634

###### 8.5.3[2].[t]*.[r][6].Inv
No
- WordTraceId: 21636

###### 8.5.3[2].[t]*.[r][6].Medium
RBC
- WordTraceId: 21639

###### 8.5.3[2].[t]*.[r][7]
- WordTraceId: 21644

###### 8.5.3[2].[t]*.[r][7].ID
15
- WordTraceId: 21644

###### 8.5.3[2].[t]*.[r][7].Name
Conditional Emergency Stop
- WordTraceId: 21647

###### 8.5.3[2].[t]*.[r][7].Type
E or N
- WordTraceId: 21674

###### 8.5.3[2].[t]*.[r][7].Inv
No
- WordTraceId: 21681

###### 8.5.3[2].[t]*.[r][7].Medium
RBC
- WordTraceId: 21684

###### 8.5.3[2].[t]*.[r][8]
- WordTraceId: 21689

###### 8.5.3[2].[t]*.[r][8].ID
16
- WordTraceId: 21689

###### 8.5.3[2].[t]*.[r][8].Name
Unconditional Emergency Stop
- WordTraceId: 21692

###### 8.5.3[2].[t]*.[r][8].Type
E or N
- WordTraceId: 21721

###### 8.5.3[2].[t]*.[r][8].Inv
No
- WordTraceId: 21728

###### 8.5.3[2].[t]*.[r][8].Medium
RBC
- WordTraceId: 21731

###### 8.5.3[2].[t]*.[r][9]
- WordTraceId: 21736

###### 8.5.3[2].[t]*.[r][9].ID
18
- WordTraceId: 21736

###### 8.5.3[2].[t]*.[r][9].Name
Revocation of Emergency Stop
- WordTraceId: 21739

###### 8.5.3[2].[t]*.[r][9].Type
N
- WordTraceId: 21768

###### 8.5.3[2].[t]*.[r][9].Inv
No
- WordTraceId: 21770

###### 8.5.3[2].[t]*.[r][9].Medium
RBC
- WordTraceId: 21773

###### 8.5.3[2].[t]*.[r][10]
- WordTraceId: 21778

###### 8.5.3[2].[t]*.[r][10].ID
24
- WordTraceId: 21778

###### 8.5.3[2].[t]*.[r][10].Name
General message
- WordTraceId: 21781

###### 8.5.3[2].[t]*.[r][10].Type
N
- WordTraceId: 21797

###### 8.5.3[2].[t]*.[r][10].Inv
No
- WordTraceId: 21799

###### 8.5.3[2].[t]*.[r][10].Medium
RBC, RIU
- WordTraceId: 21802

###### 8.5.3[2].[t]*.[r][11]
- WordTraceId: 21812

###### 8.5.3[2].[t]*.[r][11].ID
27
- WordTraceId: 21812

###### 8.5.3[2].[t]*.[r][11].Name
SH Refused
- WordTraceId: 21815

###### 8.5.3[2].[t]*.[r][11].Type
N
- WordTraceId: 21826

###### 8.5.3[2].[t]*.[r][11].Inv
No
- WordTraceId: 21828

###### 8.5.3[2].[t]*.[r][11].Medium
RBC
- WordTraceId: 21831

###### 8.5.3[2].[t]*.[r][12]
- WordTraceId: 21836

###### 8.5.3[2].[t]*.[r][12].ID
28
- WordTraceId: 21836

###### 8.5.3[2].[t]*.[r][12].Name
SH Authorised
- WordTraceId: 21839

###### 8.5.3[2].[t]*.[r][12].Type
N
- WordTraceId: 21853

###### 8.5.3[2].[t]*.[r][12].Inv
No
- WordTraceId: 21855

###### 8.5.3[2].[t]*.[r][12].Medium
RBC
- WordTraceId: 21858

###### 8.5.3[2].[t]*.[r][13]
- WordTraceId: 21863

###### 8.5.3[2].[t]*.[r][13].ID
33
- WordTraceId: 21863

###### 8.5.3[2].[t]*.[r][13].Name
MA with Shifted Location Reference
- WordTraceId: 21866

###### 8.5.3[2].[t]*.[r][13].Type
N
- WordTraceId: 21901

###### 8.5.3[2].[t]*.[r][13].Inv
No
- WordTraceId: 21903

###### 8.5.3[2].[t]*.[r][13].Medium
RBC
- WordTraceId: 21906

###### 8.5.3[2].[t]*.[r][14]
- WordTraceId: 21911

###### 8.5.3[2].[t]*.[r][14].ID
34
- WordTraceId: 21911

###### 8.5.3[2].[t]*.[r][14].Name
Track Ahead Free Request
- WordTraceId: 21914

###### 8.5.3[2].[t]*.[r][14].Type
N
- WordTraceId: 21939

###### 8.5.3[2].[t]*.[r][14].Inv
No
- WordTraceId: 21941

###### 8.5.3[2].[t]*.[r][14].Medium
RBC
- WordTraceId: 21944

###### 8.5.3[2].[t]*.[r][15]
- WordTraceId: 21949

###### 8.5.3[2].[t]*.[r][15].ID
37
- WordTraceId: 21949

###### 8.5.3[2].[t]*.[r][15].Name
Infill MA
- WordTraceId: 21952

###### 8.5.3[2].[t]*.[r][15].Type
N
- WordTraceId: 21962

###### 8.5.3[2].[t]*.[r][15].Inv
No
- WordTraceId: 21964

###### 8.5.3[2].[t]*.[r][15].Medium
RIU
- WordTraceId: 21967

###### 8.5.3[2].[t]*.[r][16]
- WordTraceId: 21972

###### 8.5.3[2].[t]*.[r][16].ID
40
- WordTraceId: 21972

###### 8.5.3[2].[t]*.[r][16].Name
Train Rejected
- WordTraceId: 21975

###### 8.5.3[2].[t]*.[r][16].Type
N
- WordTraceId: 21990

###### 8.5.3[2].[t]*.[r][16].Inv
No
- WordTraceId: 21992

###### 8.5.3[2].[t]*.[r][16].Medium
RBC
- WordTraceId: 21995

###### 8.5.3[2].[t]*.[r][17]
- WordTraceId: 22000

###### 8.5.3[2].[t]*.[r][17].ID
32
- WordTraceId: 22000

###### 8.5.3[2].[t]*.[r][17].Name
RBC/RIU System Version
- WordTraceId: 22003

###### 8.5.3[2].[t]*.[r][17].Type
N
- WordTraceId: 22026

###### 8.5.3[2].[t]*.[r][17].Inv
Yes
- WordTraceId: 22028

###### 8.5.3[2].[t]*.[r][17].Medium
RBC, RIU
- WordTraceId: 22032

###### 8.5.3[2].[t]*.[r][18]
- WordTraceId: 22042

###### 8.5.3[2].[t]*.[r][18].ID
38
- WordTraceId: 22042

###### 8.5.3[2].[t]*.[r][18].Name
Initiation of a communication session
- WordTraceId: 22045

###### 8.5.3[2].[t]*.[r][18].Type
N
- WordTraceId: 22083

###### 8.5.3[2].[t]*.[r][18].Inv
Yes
- WordTraceId: 22085

###### 8.5.3[2].[t]*.[r][18].Medium
RBC
- WordTraceId: 22089

###### 8.5.3[2].[t]*.[r][19]
- WordTraceId: 22094

###### 8.5.3[2].[t]*.[r][19].ID
39
- WordTraceId: 22094

###### 8.5.3[2].[t]*.[r][19].Name
Acknowledgement of termination of a communication session
- WordTraceId: 22097

###### 8.5.3[2].[t]*.[r][19].Type
N
- WordTraceId: 22155

###### 8.5.3[2].[t]*.[r][19].Inv
Yes
- WordTraceId: 22157

###### 8.5.3[2].[t]*.[r][19].Medium
RBC, RIU
- WordTraceId: 22161

###### 8.5.3[2].[t]*.[r][20]
- WordTraceId: 22171

###### 8.5.3[2].[t]*.[r][20].ID
41
- WordTraceId: 22171

###### 8.5.3[2].[t]*.[r][20].Name
Train Accepted
- WordTraceId: 22174

###### 8.5.3[2].[t]*.[r][20].Type
N
- WordTraceId: 22189

###### 8.5.3[2].[t]*.[r][20].Inv
No
- WordTraceId: 22191

###### 8.5.3[2].[t]*.[r][20].Medium
RBC
- WordTraceId: 22194

###### 8.5.3[2].[t]*.[r][21]
- WordTraceId: 22199

###### 8.5.3[2].[t]*.[r][21].ID
43
- WordTraceId: 22199

###### 8.5.3[2].[t]*.[r][21].Name
SoM position report confirmed by RBC
- WordTraceId: 22202

###### 8.5.3[2].[t]*.[r][21].Type
N
- WordTraceId: 22239

###### 8.5.3[2].[t]*.[r][21].Inv
No
- WordTraceId: 22241

###### 8.5.3[2].[t]*.[r][21].Medium
RBC
- WordTraceId: 22244

###### 8.5.3[2].[t]*.[r][22]
- WordTraceId: 22249

###### 8.5.3[2].[t]*.[r][22].ID
45
- WordTraceId: 22249

###### 8.5.3[2].[t]*.[r][22].Name
Assignment of coordinate system
- WordTraceId: 22252

###### 8.5.3[2].[t]*.[r][22].Type
N
- WordTraceId: 22284

###### 8.5.3[2].[t]*.[r][22].Inv
No
- WordTraceId: 22286

###### 8.5.3[2].[t]*.[r][22].Medium
RBC
- WordTraceId: 22289

#### 8.6
Definition of Radio Messages from Train to Track
- WordTraceId: 22294

##### 8.6.1
Message 129: Validated Train Data
- WordTraceId: 22343

##### 8.6.1[2]
- WordTraceId: 22378

###### 8.6.1[2].[t]*
| Field No. | VARIABLE/ PACKET | Remarks |
| --- | --- | --- |
| [r][2].Field {1} | [r][2].Variable NID_MESSAGE |  |
| [r][3].Field {2} | [r][3].Variable L_MESSAGE |  |
| [r][4].Field {3} | [r][4].Variable T_TRAIN |  |
| [r][5].Field {4} | [r][5].Variable NID_ENGINE |  |
| [r][6].Field {5} | [r][6].Variable Packet 0 or 1 |  |
| [r][7].Field {6} | [r][7].Variable Train data | [r][7].Remarks Train - track packet type 11. |
- WordTraceId: 22529

###### 8.6.1[2].[t]*.[r][2]
- WordTraceId: 22414

###### 8.6.1[2].[t]*.[r][2].Field
{1}
- PlainText: 1
- WordTraceId: 22414

###### 8.6.1[2].[t]*.[r][2].Variable
NID_MESSAGE
- WordTraceId: 22415

###### 8.6.1[2].[t]*.[r][3]
- WordTraceId: 22429

###### 8.6.1[2].[t]*.[r][3].Field
{2}
- PlainText: 2
- WordTraceId: 22429

###### 8.6.1[2].[t]*.[r][3].Variable
L_MESSAGE
- WordTraceId: 22430

###### 8.6.1[2].[t]*.[r][4]
- WordTraceId: 22442

###### 8.6.1[2].[t]*.[r][4].Field
{3}
- PlainText: 3
- WordTraceId: 22442

###### 8.6.1[2].[t]*.[r][4].Variable
T_TRAIN
- WordTraceId: 22443

###### 8.6.1[2].[t]*.[r][5]
- WordTraceId: 22453

###### 8.6.1[2].[t]*.[r][5].Field
{4}
- PlainText: 4
- WordTraceId: 22453

###### 8.6.1[2].[t]*.[r][5].Variable
NID_ENGINE
- WordTraceId: 22454

###### 8.6.1[2].[t]*.[r][6]
- WordTraceId: 22467

###### 8.6.1[2].[t]*.[r][6].Field
{5}
- PlainText: 5
- WordTraceId: 22467

###### 8.6.1[2].[t]*.[r][6].Variable
Packet 0 or 1
- WordTraceId: 22468

###### 8.6.1[2].[t]*.[r][7]
- WordTraceId: 22484

###### 8.6.1[2].[t]*.[r][7].Field
{6}
- PlainText: 6
- WordTraceId: 22484

###### 8.6.1[2].[t]*.[r][7].Variable
Train data
- WordTraceId: 22485

###### 8.6.1[2].[t]*.[r][7].Remarks
Train - track packet type 11.
- WordTraceId: 22496

##### 8.6.2
Message 130: Request for Shunting
- WordTraceId: 22529

##### 8.6.2[2]
- WordTraceId: 22564

###### 8.6.2[2].[t]*
| Field No. | VARIABLE/ PACKET | Remarks |
| --- | --- | --- |
| [r][2].Field {1} | [r][2].Variable NID_MESSAGE |  |
| [r][3].Field {2} | [r][3].Variable L_MESSAGE |  |
| [r][4].Field {3} | [r][4].Variable T_TRAIN |  |
| [r][5].Field {4} | [r][5].Variable NID_ENGINE |  |
| [r][6].Field {5} | [r][6].Variable Packet 0 or 1 |  |
- WordTraceId: 22671

###### 8.6.2[2].[t]*.[r][2]
- WordTraceId: 22600

###### 8.6.2[2].[t]*.[r][2].Field
{1}
- PlainText: 1
- WordTraceId: 22600

###### 8.6.2[2].[t]*.[r][2].Variable
NID_MESSAGE
- WordTraceId: 22601

###### 8.6.2[2].[t]*.[r][3]
- WordTraceId: 22615

###### 8.6.2[2].[t]*.[r][3].Field
{2}
- PlainText: 2
- WordTraceId: 22615

###### 8.6.2[2].[t]*.[r][3].Variable
L_MESSAGE
- WordTraceId: 22616

###### 8.6.2[2].[t]*.[r][4]
- WordTraceId: 22628

###### 8.6.2[2].[t]*.[r][4].Field
{3}
- PlainText: 3
- WordTraceId: 22628

###### 8.6.2[2].[t]*.[r][4].Variable
T_TRAIN
- WordTraceId: 22629

###### 8.6.2[2].[t]*.[r][5]
- WordTraceId: 22639

###### 8.6.2[2].[t]*.[r][5].Field
{4}
- PlainText: 4
- WordTraceId: 22639

###### 8.6.2[2].[t]*.[r][5].Variable
NID_ENGINE
- WordTraceId: 22640

###### 8.6.2[2].[t]*.[r][6]
- WordTraceId: 22653

###### 8.6.2[2].[t]*.[r][6].Field
{5}
- PlainText: 5
- WordTraceId: 22653

###### 8.6.2[2].[t]*.[r][6].Variable
Packet 0 or 1
- WordTraceId: 22654

##### 8.6.3
Message 132: MA Request
- WordTraceId: 22671

##### 8.6.3[2]
- WordTraceId: 22696

###### 8.6.3[2].[t]*
| Field No. | VARIABLE/ PACKET | Remarks |
| --- | --- | --- |
| [r][2].Field {1} | [r][2].Variable NID_MESSAGE |  |
| [r][3].Field {2} | [r][3].Variable L_MESSAGE |  |
| [r][4].Field {3} | [r][4].Variable T_TRAIN |  |
| [r][5].Field {4} | [r][5].Variable NID_ENGINE |  |
| [r][6].Field {5} | [r][6].Variable Q_ MARQSTREASON |  |
| [r][7].Field {6} | [r][7].Variable Packet 0 or 1 |  |
| [r][8].Field {7} | [r][8].Variable Optional packets |  |
- WordTraceId: 22841

###### 8.6.3[2].[t]*.[r][2]
- WordTraceId: 22732

###### 8.6.3[2].[t]*.[r][2].Field
{1}
- PlainText: 1
- WordTraceId: 22732

###### 8.6.3[2].[t]*.[r][2].Variable
NID_MESSAGE
- WordTraceId: 22733

###### 8.6.3[2].[t]*.[r][3]
- WordTraceId: 22747

###### 8.6.3[2].[t]*.[r][3].Field
{2}
- PlainText: 2
- WordTraceId: 22747

###### 8.6.3[2].[t]*.[r][3].Variable
L_MESSAGE
- WordTraceId: 22748

###### 8.6.3[2].[t]*.[r][4]
- WordTraceId: 22760

###### 8.6.3[2].[t]*.[r][4].Field
{3}
- PlainText: 3
- WordTraceId: 22760

###### 8.6.3[2].[t]*.[r][4].Variable
T_TRAIN
- WordTraceId: 22761

###### 8.6.3[2].[t]*.[r][5]
- WordTraceId: 22771

###### 8.6.3[2].[t]*.[r][5].Field
{4}
- PlainText: 4
- WordTraceId: 22771

###### 8.6.3[2].[t]*.[r][5].Variable
NID_ENGINE
- WordTraceId: 22772

###### 8.6.3[2].[t]*.[r][6]
- WordTraceId: 22785

###### 8.6.3[2].[t]*.[r][6].Field
{5}
- PlainText: 5
- WordTraceId: 22785

###### 8.6.3[2].[t]*.[r][6].Variable
Q_ MARQSTREASON
- PlainText: Q_MARQSTREASON
- WordTraceId: 22786

###### 8.6.3[2].[t]*.[r][7]
- WordTraceId: 22803

###### 8.6.3[2].[t]*.[r][7].Field
{6}
- PlainText: 6
- WordTraceId: 22803

###### 8.6.3[2].[t]*.[r][7].Variable
Packet 0 or 1
- WordTraceId: 22804

###### 8.6.3[2].[t]*.[r][8]
- WordTraceId: 22820

###### 8.6.3[2].[t]*.[r][8].Field
{7}
- PlainText: 7
- WordTraceId: 22820

###### 8.6.3[2].[t]*.[r][8].Variable
Optional packets
- WordTraceId: 22821

##### 8.6.4
Message 136: Train Position Report
- WordTraceId: 22841

##### 8.6.4[2]
- WordTraceId: 22877

###### 8.6.4[2].[t]*
| Field No. | VARIABLE/ PACKET | Remarks |
| --- | --- | --- |
| [r][2].Field {1} | [r][2].Variable NID_MESSAGE |  |
| [r][3].Field {2} | [r][3].Variable L_MESSAGE |  |
| [r][4].Field {3} | [r][4].Variable T_TRAIN |  |
| [r][5].Field {4} | [r][5].Variable NID_ENGINE |  |
| [r][6].Field {5} | [r][6].Variable Packet 0 or 1 |  |
| [r][7].Field {6} | [r][7].Variable Optional packets |  |
- WordTraceId: 23004

###### 8.6.4[2].[t]*.[r][2]
- WordTraceId: 22913

###### 8.6.4[2].[t]*.[r][2].Field
{1}
- PlainText: 1
- WordTraceId: 22913

###### 8.6.4[2].[t]*.[r][2].Variable
NID_MESSAGE
- WordTraceId: 22914

###### 8.6.4[2].[t]*.[r][3]
- WordTraceId: 22928

###### 8.6.4[2].[t]*.[r][3].Field
{2}
- PlainText: 2
- WordTraceId: 22928

###### 8.6.4[2].[t]*.[r][3].Variable
L_MESSAGE
- WordTraceId: 22929

###### 8.6.4[2].[t]*.[r][4]
- WordTraceId: 22941

###### 8.6.4[2].[t]*.[r][4].Field
{3}
- PlainText: 3
- WordTraceId: 22941

###### 8.6.4[2].[t]*.[r][4].Variable
T_TRAIN
- WordTraceId: 22942

###### 8.6.4[2].[t]*.[r][5]
- WordTraceId: 22952

###### 8.6.4[2].[t]*.[r][5].Field
{4}
- PlainText: 4
- WordTraceId: 22952

###### 8.6.4[2].[t]*.[r][5].Variable
NID_ENGINE
- WordTraceId: 22953

###### 8.6.4[2].[t]*.[r][6]
- WordTraceId: 22966

###### 8.6.4[2].[t]*.[r][6].Field
{5}
- PlainText: 5
- WordTraceId: 22966

###### 8.6.4[2].[t]*.[r][6].Variable
Packet 0 or 1
- WordTraceId: 22967

###### 8.6.4[2].[t]*.[r][7]
- WordTraceId: 22983

###### 8.6.4[2].[t]*.[r][7].Field
{6}
- PlainText: 6
- WordTraceId: 22983

###### 8.6.4[2].[t]*.[r][7].Variable
Optional packets
- WordTraceId: 22984

##### 8.6.5
Message 137: Request to Shorten MA is granted
- WordTraceId: 23004

##### 8.6.5[2]
- WordTraceId: 23051

###### 8.6.5[2].[t]*
| Field No. | VARIABLE/ PACKET | Remarks |
| --- | --- | --- |
| [r][2].Field {1} | [r][2].Variable NID_MESSAGE |  |
| [r][3].Field {2} | [r][3].Variable L_MESSAGE |  |
| [r][4].Field {3} | [r][4].Variable T_TRAIN |  |
| [r][5].Field {4} | [r][5].Variable NID_ENGINE |  |
| [r][6].Field {5} | [r][6].Variable T_TRAIN | [r][6].Remarks Time stamp contained in the request. |
| [r][7].Field {6} | [r][7].Variable Packet 0 or 1 |  |
- WordTraceId: 23205

###### 8.6.5[2].[t]*.[r][2]
- WordTraceId: 23087

###### 8.6.5[2].[t]*.[r][2].Field
{1}
- PlainText: 1
- WordTraceId: 23087

###### 8.6.5[2].[t]*.[r][2].Variable
NID_MESSAGE
- WordTraceId: 23088

###### 8.6.5[2].[t]*.[r][3]
- WordTraceId: 23102

###### 8.6.5[2].[t]*.[r][3].Field
{2}
- PlainText: 2
- WordTraceId: 23102

###### 8.6.5[2].[t]*.[r][3].Variable
L_MESSAGE
- WordTraceId: 23103

###### 8.6.5[2].[t]*.[r][4]
- WordTraceId: 23115

###### 8.6.5[2].[t]*.[r][4].Field
{3}
- PlainText: 3
- WordTraceId: 23115

###### 8.6.5[2].[t]*.[r][4].Variable
T_TRAIN
- WordTraceId: 23116

###### 8.6.5[2].[t]*.[r][5]
- WordTraceId: 23126

###### 8.6.5[2].[t]*.[r][5].Field
{4}
- PlainText: 4
- WordTraceId: 23126

###### 8.6.5[2].[t]*.[r][5].Variable
NID_ENGINE
- WordTraceId: 23127

###### 8.6.5[2].[t]*.[r][6]
- WordTraceId: 23140

###### 8.6.5[2].[t]*.[r][6].Field
{5}
- PlainText: 5
- WordTraceId: 23140

###### 8.6.5[2].[t]*.[r][6].Variable
T_TRAIN
- WordTraceId: 23141

###### 8.6.5[2].[t]*.[r][6].Remarks
Time stamp contained in the request.
- WordTraceId: 23149

###### 8.6.5[2].[t]*.[r][7]
- WordTraceId: 23187

###### 8.6.5[2].[t]*.[r][7].Field
{6}
- PlainText: 6
- WordTraceId: 23187

###### 8.6.5[2].[t]*.[r][7].Variable
Packet 0 or 1
- WordTraceId: 23188

##### 8.6.6
Message 138: Request to Shorten MA is rejected
- WordTraceId: 23205

##### 8.6.6[2]
- WordTraceId: 23253

###### 8.6.6[2].[t]*
| Field No. | VARIABLE/ PACKET | Remarks |
| --- | --- | --- |
| [r][2].Field {1} | [r][2].Variable NID_MESSAGE |  |
| [r][3].Field {2} | [r][3].Variable L_MESSAGE |  |
| [r][4].Field {3} | [r][4].Variable T_TRAIN |  |
| [r][5].Field {4} | [r][5].Variable NID_ENGINE |  |
| [r][6].Field {5} | [r][6].Variable T_TRAIN | [r][6].Remarks Time stamp contained in the request. |
| [r][7].Field {6} | [r][7].Variable Packet 0 or 1 |  |
- WordTraceId: 23407

###### 8.6.6[2].[t]*.[r][2]
- WordTraceId: 23289

###### 8.6.6[2].[t]*.[r][2].Field
{1}
- PlainText: 1
- WordTraceId: 23289

###### 8.6.6[2].[t]*.[r][2].Variable
NID_MESSAGE
- WordTraceId: 23290

###### 8.6.6[2].[t]*.[r][3]
- WordTraceId: 23304

###### 8.6.6[2].[t]*.[r][3].Field
{2}
- PlainText: 2
- WordTraceId: 23304

###### 8.6.6[2].[t]*.[r][3].Variable
L_MESSAGE
- WordTraceId: 23305

###### 8.6.6[2].[t]*.[r][4]
- WordTraceId: 23317

###### 8.6.6[2].[t]*.[r][4].Field
{3}
- PlainText: 3
- WordTraceId: 23317

###### 8.6.6[2].[t]*.[r][4].Variable
T_TRAIN
- WordTraceId: 23318

###### 8.6.6[2].[t]*.[r][5]
- WordTraceId: 23328

###### 8.6.6[2].[t]*.[r][5].Field
{4}
- PlainText: 4
- WordTraceId: 23328

###### 8.6.6[2].[t]*.[r][5].Variable
NID_ENGINE
- WordTraceId: 23329

###### 8.6.6[2].[t]*.[r][6]
- WordTraceId: 23342

###### 8.6.6[2].[t]*.[r][6].Field
{5}
- PlainText: 5
- WordTraceId: 23342

###### 8.6.6[2].[t]*.[r][6].Variable
T_TRAIN
- WordTraceId: 23343

###### 8.6.6[2].[t]*.[r][6].Remarks
Time stamp contained in the request.
- WordTraceId: 23351

###### 8.6.6[2].[t]*.[r][7]
- WordTraceId: 23389

###### 8.6.6[2].[t]*.[r][7].Field
{6}
- PlainText: 6
- WordTraceId: 23389

###### 8.6.6[2].[t]*.[r][7].Variable
Packet 0 or 1
- WordTraceId: 23390

##### 8.6.7
Message 146: Acknowledgement
- WordTraceId: 23407

##### 8.6.7[2]
- WordTraceId: 23437

###### 8.6.7[2].[t]*
| Field No. | VARIABLE | Remarks |
| --- | --- | --- |
| [r][2].Field {1} | [r][2].Variable NID_MESSAGE |  |
| [r][3].Field {2} | [r][3].Variable L_MESSAGE |  |
| [r][4].Field {3} | [r][4].Variable T_TRAIN |  |
| [r][5].Field {4} | [r][5].Variable NID_ENGINE |  |
| [r][6].Field {5} | [r][6].Variable T_TRAIN | [r][6].Remarks Time stamp contained in the message that is acknowledged. |
- WordTraceId: 23588

###### 8.6.7[2].[t]*.[r][2]
- WordTraceId: 23465

###### 8.6.7[2].[t]*.[r][2].Field
{1}
- PlainText: 1
- WordTraceId: 23465

###### 8.6.7[2].[t]*.[r][2].Variable
NID_MESSAGE
- WordTraceId: 23466

###### 8.6.7[2].[t]*.[r][3]
- WordTraceId: 23480

###### 8.6.7[2].[t]*.[r][3].Field
{2}
- PlainText: 2
- WordTraceId: 23480

###### 8.6.7[2].[t]*.[r][3].Variable
L_MESSAGE
- WordTraceId: 23481

###### 8.6.7[2].[t]*.[r][4]
- WordTraceId: 23493

###### 8.6.7[2].[t]*.[r][4].Field
{3}
- PlainText: 3
- WordTraceId: 23493

###### 8.6.7[2].[t]*.[r][4].Variable
T_TRAIN
- WordTraceId: 23494

###### 8.6.7[2].[t]*.[r][5]
- WordTraceId: 23504

###### 8.6.7[2].[t]*.[r][5].Field
{4}
- PlainText: 4
- WordTraceId: 23504

###### 8.6.7[2].[t]*.[r][5].Variable
NID_ENGINE
- WordTraceId: 23505

###### 8.6.7[2].[t]*.[r][6]
- WordTraceId: 23518

###### 8.6.7[2].[t]*.[r][6].Field
{5}
- PlainText: 5
- WordTraceId: 23518

###### 8.6.7[2].[t]*.[r][6].Variable
T_TRAIN
- WordTraceId: 23519

###### 8.6.7[2].[t]*.[r][6].Remarks
Time stamp contained in the message that is acknowledged.
- WordTraceId: 23528

##### 8.6.8
Message 147: Acknowledgement of Emergency Stop
- WordTraceId: 23588

##### 8.6.8[2]
- WordTraceId: 23636

###### 8.6.8[2].[t]*
| Field No. | VARIABLE | Remarks |
| --- | --- | --- |
| [r][2].Field {1} | [r][2].Variable NID_MESSAGE |  |
| [r][3].Field {2} | [r][3].Variable L_MESSAGE |  |
| [r][4].Field {3} | [r][4].Variable T_TRAIN |  |
| [r][5].Field {4} | [r][5].Variable NID_ENGINE |  |
| [r][6].Field {5} | [r][6].Variable NID_EM | [r][6].Remarks Identification Number of the acknowledged Emergency Message. |
| [r][7].Field {6} | [r][7].Variable Q_EMERGENCYSTOP |  |
| [r][8].Field {7} | [r][8].Variable Packet 0 or 1 |  |
- WordTraceId: 23824

###### 8.6.8[2].[t]*.[r][2]
- WordTraceId: 23664

###### 8.6.8[2].[t]*.[r][2].Field
{1}
- PlainText: 1
- WordTraceId: 23664

###### 8.6.8[2].[t]*.[r][2].Variable
NID_MESSAGE
- WordTraceId: 23665

###### 8.6.8[2].[t]*.[r][3]
- WordTraceId: 23679

###### 8.6.8[2].[t]*.[r][3].Field
{2}
- PlainText: 2
- WordTraceId: 23679

###### 8.6.8[2].[t]*.[r][3].Variable
L_MESSAGE
- WordTraceId: 23680

###### 8.6.8[2].[t]*.[r][4]
- WordTraceId: 23692

###### 8.6.8[2].[t]*.[r][4].Field
{3}
- PlainText: 3
- WordTraceId: 23692

###### 8.6.8[2].[t]*.[r][4].Variable
T_TRAIN
- WordTraceId: 23693

###### 8.6.8[2].[t]*.[r][5]
- WordTraceId: 23703

###### 8.6.8[2].[t]*.[r][5].Field
{4}
- PlainText: 4
- WordTraceId: 23703

###### 8.6.8[2].[t]*.[r][5].Variable
NID_ENGINE
- WordTraceId: 23704

###### 8.6.8[2].[t]*.[r][6]
- WordTraceId: 23717

###### 8.6.8[2].[t]*.[r][6].Field
{5}
- PlainText: 5
- WordTraceId: 23717

###### 8.6.8[2].[t]*.[r][6].Variable
NID_EM
- WordTraceId: 23718

###### 8.6.8[2].[t]*.[r][6].Remarks
Identification Number of the acknowledged Emergency Message.
- WordTraceId: 23725

###### 8.6.8[2].[t]*.[r][7]
- WordTraceId: 23787

###### 8.6.8[2].[t]*.[r][7].Field
{6}
- PlainText: 6
- WordTraceId: 23787

###### 8.6.8[2].[t]*.[r][7].Variable
Q_EMERGENCYSTOP
- WordTraceId: 23788

###### 8.6.8[2].[t]*.[r][8]
- WordTraceId: 23806

###### 8.6.8[2].[t]*.[r][8].Field
{7}
- PlainText: 7
- WordTraceId: 23806

###### 8.6.8[2].[t]*.[r][8].Variable
Packet 0 or 1
- WordTraceId: 23807

##### 8.6.9
Message 149: Track Ahead Free Granted
- WordTraceId: 23824

##### 8.6.9[2]
- WordTraceId: 23863

###### 8.6.9[2].[t]*
| Field No. | VARIABLE/ PACKET | Remarks |
| --- | --- | --- |
| [r][2].Field {1} | [r][2].Variable NID_MESSAGE |  |
| [r][3].Field {2} | [r][3].Variable L_MESSAGE |  |
| [r][4].Field {3} | [r][4].Variable T_TRAIN |  |
| [r][5].Field {4} | [r][5].Variable NID_ENGINE |  |
| [r][6].Field {5} | [r][6].Variable Packet 0 or 1 |  |
- WordTraceId: 23970

###### 8.6.9[2].[t]*.[r][2]
- WordTraceId: 23899

###### 8.6.9[2].[t]*.[r][2].Field
{1}
- PlainText: 1
- WordTraceId: 23899

###### 8.6.9[2].[t]*.[r][2].Variable
NID_MESSAGE
- WordTraceId: 23900

###### 8.6.9[2].[t]*.[r][3]
- WordTraceId: 23914

###### 8.6.9[2].[t]*.[r][3].Field
{2}
- PlainText: 2
- WordTraceId: 23914

###### 8.6.9[2].[t]*.[r][3].Variable
L_MESSAGE
- WordTraceId: 23915

###### 8.6.9[2].[t]*.[r][4]
- WordTraceId: 23927

###### 8.6.9[2].[t]*.[r][4].Field
{3}
- PlainText: 3
- WordTraceId: 23927

###### 8.6.9[2].[t]*.[r][4].Variable
T_TRAIN
- WordTraceId: 23928

###### 8.6.9[2].[t]*.[r][5]
- WordTraceId: 23938

###### 8.6.9[2].[t]*.[r][5].Field
{4}
- PlainText: 4
- WordTraceId: 23938

###### 8.6.9[2].[t]*.[r][5].Variable
NID_ENGINE
- WordTraceId: 23939

###### 8.6.9[2].[t]*.[r][6]
- WordTraceId: 23952

###### 8.6.9[2].[t]*.[r][6].Field
{5}
- PlainText: 5
- WordTraceId: 23952

###### 8.6.9[2].[t]*.[r][6].Variable
Packet 0 or 1
- WordTraceId: 23953

##### 8.6.10
Message 150: End of Mission
- WordTraceId: 23971

##### 8.6.10[2]
- WordTraceId: 24000

###### 8.6.10[2].[t]*
| Field No. | VARIABLE/ PACKET | Remarks |
| --- | --- | --- |
| [r][2].Field {1} | [r][2].Variable NID_MESSAGE |  |
| [r][3].Field {2} | [r][3].Variable L_MESSAGE |  |
| [r][4].Field {3} | [r][4].Variable T_TRAIN |  |
| [r][5].Field {4} | [r][5].Variable NID_ENGINE |  |
| [r][6].Field {5} | [r][6].Variable Packet 0 or 1 |  |
- WordTraceId: 24107

###### 8.6.10[2].[t]*.[r][2]
- WordTraceId: 24036

###### 8.6.10[2].[t]*.[r][2].Field
{1}
- PlainText: 1
- WordTraceId: 24036

###### 8.6.10[2].[t]*.[r][2].Variable
NID_MESSAGE
- WordTraceId: 24037

###### 8.6.10[2].[t]*.[r][3]
- WordTraceId: 24051

###### 8.6.10[2].[t]*.[r][3].Field
{2}
- PlainText: 2
- WordTraceId: 24051

###### 8.6.10[2].[t]*.[r][3].Variable
L_MESSAGE
- WordTraceId: 24052

###### 8.6.10[2].[t]*.[r][4]
- WordTraceId: 24064

###### 8.6.10[2].[t]*.[r][4].Field
{3}
- PlainText: 3
- WordTraceId: 24064

###### 8.6.10[2].[t]*.[r][4].Variable
T_TRAIN
- WordTraceId: 24065

###### 8.6.10[2].[t]*.[r][5]
- WordTraceId: 24075

###### 8.6.10[2].[t]*.[r][5].Field
{4}
- PlainText: 4
- WordTraceId: 24075

###### 8.6.10[2].[t]*.[r][5].Variable
NID_ENGINE
- WordTraceId: 24076

###### 8.6.10[2].[t]*.[r][6]
- WordTraceId: 24089

###### 8.6.10[2].[t]*.[r][6].Field
{5}
- PlainText: 5
- WordTraceId: 24089

###### 8.6.10[2].[t]*.[r][6].Variable
Packet 0 or 1
- WordTraceId: 24090

##### 8.6.11
Message 153: Radio infill request
- WordTraceId: 24107

##### 8.6.11[2]
- WordTraceId: 24142

###### 8.6.11[2].[t]*
| Field No. | VARIABLE | Remarks |
| --- | --- | --- |
| [r][2].Field {1} | [r][2].Variable NID_ MESSAGE |  |
| [r][3].Field {2} | [r][3].Variable L_ MESSAGE |  |
| [r][4].Field {3} | [r][4].Variable T_TRAIN |  |
| [r][5].Field {4} | [r][5].Variable NID_ENGINE |  |
| [r][6].Field {5} | [r][6].Variable NID_C | [r][6].Remarks identity of the country of the “target” main balise group |
| [r][7].Field {6} | [r][7].Variable NID_BG | [r][7].Remarks identity of the “target” main balise group |
| [r][8].Field {7} | [r][8].Variable Q_INFILL | [r][8].Remarks start; end of infill |
| [r][9].Field {8} | [r][9].Variable Packet 0 or 1 |  |
- WordTraceId: 24391

###### 8.6.11[2].[t]*.[r][2]
- WordTraceId: 24170

###### 8.6.11[2].[t]*.[r][2].Field
{1}
- PlainText: 1
- WordTraceId: 24170

###### 8.6.11[2].[t]*.[r][2].Variable
NID_ MESSAGE
- PlainText: NID_MESSAGE
- WordTraceId: 24171

###### 8.6.11[2].[t]*.[r][3]
- WordTraceId: 24185

###### 8.6.11[2].[t]*.[r][3].Field
{2}
- PlainText: 2
- WordTraceId: 24185

###### 8.6.11[2].[t]*.[r][3].Variable
L_ MESSAGE
- PlainText: L_MESSAGE
- WordTraceId: 24186

###### 8.6.11[2].[t]*.[r][4]
- WordTraceId: 24198

###### 8.6.11[2].[t]*.[r][4].Field
{3}
- PlainText: 3
- WordTraceId: 24198

###### 8.6.11[2].[t]*.[r][4].Variable
T_TRAIN
- WordTraceId: 24199

###### 8.6.11[2].[t]*.[r][5]
- WordTraceId: 24209

###### 8.6.11[2].[t]*.[r][5].Field
{4}
- PlainText: 4
- WordTraceId: 24209

###### 8.6.11[2].[t]*.[r][5].Variable
NID_ENGINE
- WordTraceId: 24210

###### 8.6.11[2].[t]*.[r][6]
- WordTraceId: 24223

###### 8.6.11[2].[t]*.[r][6].Field
{5}
- PlainText: 5
- WordTraceId: 24223

###### 8.6.11[2].[t]*.[r][6].Variable
NID_C
- WordTraceId: 24224

###### 8.6.11[2].[t]*.[r][6].Remarks
identity of the country of the “target” main balise group
- WordTraceId: 24230

###### 8.6.11[2].[t]*.[r][7]
- WordTraceId: 24289

###### 8.6.11[2].[t]*.[r][7].Field
{6}
- PlainText: 6
- WordTraceId: 24289

###### 8.6.11[2].[t]*.[r][7].Variable
NID_BG
- WordTraceId: 24290

###### 8.6.11[2].[t]*.[r][7].Remarks
identity of the “target” main balise group
- WordTraceId: 24297

###### 8.6.11[2].[t]*.[r][8]
- WordTraceId: 24341

###### 8.6.11[2].[t]*.[r][8].Field
{7}
- PlainText: 7
- WordTraceId: 24341

###### 8.6.11[2].[t]*.[r][8].Variable
Q_INFILL
- WordTraceId: 24342

###### 8.6.11[2].[t]*.[r][8].Remarks
start; end of infill
- WordTraceId: 24351

###### 8.6.11[2].[t]*.[r][9]
- WordTraceId: 24373

###### 8.6.11[2].[t]*.[r][9].Field
{8}
- PlainText: 8
- WordTraceId: 24373

###### 8.6.11[2].[t]*.[r][9].Variable
Packet 0 or 1
- WordTraceId: 24374

##### 8.6.12
Message 154: No compatible version supported
- WordTraceId: 24392

##### 8.6.12[2]
- WordTraceId: 24438

###### 8.6.12[2].[t]*
| Field No. | VARIABLE/ PACKET | Remarks |
| --- | --- | --- |
| [r][2].Field {1} | [r][2].Variable NID_MESSAGE |  |
| [r][3].Field {2} | [r][3].Variable L_MESSAGE |  |
| [r][4].Field {3} | [r][4].Variable T_TRAIN |  |
| [r][5].Field {4} | [r][5].Variable NID_ENGINE |  |
- WordTraceId: 24528

###### 8.6.12[2].[t]*.[r][2]
- WordTraceId: 24474

###### 8.6.12[2].[t]*.[r][2].Field
{1}
- PlainText: 1
- WordTraceId: 24474

###### 8.6.12[2].[t]*.[r][2].Variable
NID_MESSAGE
- WordTraceId: 24475

###### 8.6.12[2].[t]*.[r][3]
- WordTraceId: 24489

###### 8.6.12[2].[t]*.[r][3].Field
{2}
- PlainText: 2
- WordTraceId: 24489

###### 8.6.12[2].[t]*.[r][3].Variable
L_MESSAGE
- WordTraceId: 24490

###### 8.6.12[2].[t]*.[r][4]
- WordTraceId: 24502

###### 8.6.12[2].[t]*.[r][4].Field
{3}
- PlainText: 3
- WordTraceId: 24502

###### 8.6.12[2].[t]*.[r][4].Variable
T_TRAIN
- WordTraceId: 24503

###### 8.6.12[2].[t]*.[r][5]
- WordTraceId: 24513

###### 8.6.12[2].[t]*.[r][5].Field
{4}
- PlainText: 4
- WordTraceId: 24513

###### 8.6.12[2].[t]*.[r][5].Variable
NID_ENGINE
- WordTraceId: 24514

##### 8.6.13
Message 155: Initiation of a communication session
- WordTraceId: 24528

##### 8.6.13[2]
- WordTraceId: 24580

###### 8.6.13[2].[t]*
| Field No. | VARIABLE/ PACKET | Remarks |
| --- | --- | --- |
| [r][2].Field {1} | [r][2].Variable NID_MESSAGE |  |
| [r][3].Field {2} | [r][3].Variable L_MESSAGE |  |
| [r][4].Field {3} | [r][4].Variable T_TRAIN |  |
| [r][5].Field {4} | [r][5].Variable NID_ENGINE |  |
- WordTraceId: 24670

###### 8.6.13[2].[t]*.[r][2]
- WordTraceId: 24616

###### 8.6.13[2].[t]*.[r][2].Field
{1}
- PlainText: 1
- WordTraceId: 24616

###### 8.6.13[2].[t]*.[r][2].Variable
NID_MESSAGE
- WordTraceId: 24617

###### 8.6.13[2].[t]*.[r][3]
- WordTraceId: 24631

###### 8.6.13[2].[t]*.[r][3].Field
{2}
- PlainText: 2
- WordTraceId: 24631

###### 8.6.13[2].[t]*.[r][3].Variable
L_MESSAGE
- WordTraceId: 24632

###### 8.6.13[2].[t]*.[r][4]
- WordTraceId: 24644

###### 8.6.13[2].[t]*.[r][4].Field
{3}
- PlainText: 3
- WordTraceId: 24644

###### 8.6.13[2].[t]*.[r][4].Variable
T_TRAIN
- WordTraceId: 24645

###### 8.6.13[2].[t]*.[r][5]
- WordTraceId: 24655

###### 8.6.13[2].[t]*.[r][5].Field
{4}
- PlainText: 4
- WordTraceId: 24655

###### 8.6.13[2].[t]*.[r][5].Variable
NID_ENGINE
- WordTraceId: 24656

##### 8.6.14
Message 156: Termination of a communication session
- WordTraceId: 24670

##### 8.6.14[2]
- WordTraceId: 24723

###### 8.6.14[2].[t]*
| Field No. | VARIABLE/ PACKET | Remarks |
| --- | --- | --- |
| [r][2].Field {1} | [r][2].Variable NID_MESSAGE |  |
| [r][3].Field {2} | [r][3].Variable L_MESSAGE |  |
| [r][4].Field {3} | [r][4].Variable T_TRAIN |  |
| [r][5].Field {4} | [r][5].Variable NID_ENGINE |  |
- WordTraceId: 24813

###### 8.6.14[2].[t]*.[r][2]
- WordTraceId: 24759

###### 8.6.14[2].[t]*.[r][2].Field
{1}
- PlainText: 1
- WordTraceId: 24759

###### 8.6.14[2].[t]*.[r][2].Variable
NID_MESSAGE
- WordTraceId: 24760

###### 8.6.14[2].[t]*.[r][3]
- WordTraceId: 24774

###### 8.6.14[2].[t]*.[r][3].Field
{2}
- PlainText: 2
- WordTraceId: 24774

###### 8.6.14[2].[t]*.[r][3].Variable
L_MESSAGE
- WordTraceId: 24775

###### 8.6.14[2].[t]*.[r][4]
- WordTraceId: 24787

###### 8.6.14[2].[t]*.[r][4].Field
{3}
- PlainText: 3
- WordTraceId: 24787

###### 8.6.14[2].[t]*.[r][4].Variable
T_TRAIN
- WordTraceId: 24788

###### 8.6.14[2].[t]*.[r][5]
- WordTraceId: 24798

###### 8.6.14[2].[t]*.[r][5].Field
{4}
- PlainText: 4
- WordTraceId: 24798

###### 8.6.14[2].[t]*.[r][5].Variable
NID_ENGINE
- WordTraceId: 24799

##### 8.6.15
Message 157: SoM Position Report
- WordTraceId: 24814

##### 8.6.15[2]
- WordTraceId: 24848

###### 8.6.15[2].[t]*
| Field No. | VARIABLE/ PACKET | Remarks |
| --- | --- | --- |
| [r][2].Field {1} | [r][2].Variable NID_MESSAGE |  |
| [r][3].Field {2} | [r][3].Variable L_MESSAGE |  |
| [r][4].Field {3} | [r][4].Variable T_TRAIN |  |
| [r][5].Field {4} | [r][5].Variable NID_ENGINE |  |
| [r][6].Field {5} | [r][6].Variable Q_STATUS |  |
| [r][7].Field {6} | [r][7].Variable Packet 0 or 1 |  |
| [r][8].Field {7} | [r][8].Variable Optional packets |  |
- WordTraceId: 24987

###### 8.6.15[2].[t]*.[r][2]
- WordTraceId: 24884

###### 8.6.15[2].[t]*.[r][2].Field
{1}
- PlainText: 1
- WordTraceId: 24884

###### 8.6.15[2].[t]*.[r][2].Variable
NID_MESSAGE
- WordTraceId: 24885

###### 8.6.15[2].[t]*.[r][3]
- WordTraceId: 24899

###### 8.6.15[2].[t]*.[r][3].Field
{2}
- PlainText: 2
- WordTraceId: 24899

###### 8.6.15[2].[t]*.[r][3].Variable
L_MESSAGE
- WordTraceId: 24900

###### 8.6.15[2].[t]*.[r][4]
- WordTraceId: 24912

###### 8.6.15[2].[t]*.[r][4].Field
{3}
- PlainText: 3
- WordTraceId: 24912

###### 8.6.15[2].[t]*.[r][4].Variable
T_TRAIN
- WordTraceId: 24913

###### 8.6.15[2].[t]*.[r][5]
- WordTraceId: 24923

###### 8.6.15[2].[t]*.[r][5].Field
{4}
- PlainText: 4
- WordTraceId: 24923

###### 8.6.15[2].[t]*.[r][5].Variable
NID_ENGINE
- WordTraceId: 24924

###### 8.6.15[2].[t]*.[r][6]
- WordTraceId: 24937

###### 8.6.15[2].[t]*.[r][6].Field
{5}
- PlainText: 5
- WordTraceId: 24937

###### 8.6.15[2].[t]*.[r][6].Variable
Q_STATUS
- WordTraceId: 24938

###### 8.6.15[2].[t]*.[r][7]
- WordTraceId: 24949

###### 8.6.15[2].[t]*.[r][7].Field
{6}
- PlainText: 6
- WordTraceId: 24949

###### 8.6.15[2].[t]*.[r][7].Variable
Packet 0 or 1
- WordTraceId: 24950

###### 8.6.15[2].[t]*.[r][8]
- WordTraceId: 24966

###### 8.6.15[2].[t]*.[r][8].Field
{7}
- PlainText: 7
- WordTraceId: 24966

###### 8.6.15[2].[t]*.[r][8].Variable
Optional packets
- WordTraceId: 24967

##### 8.6.16
Message 1 5 8: Text Message Acknowledged by Driver
- PlainText: Message 158: Text Message Acknowledged by Driver
- WordTraceId: 24988

##### 8.6.16[2]
- WordTraceId: 25038

###### 8.6.16[2].[t]*
| Field No. | VARIABLE/ PACKET | Remarks |
| --- | --- | --- |
| [r][2].Field {1} | [r][2].Variable NID_MESSAGE |  |
| [r][3].Field {2} | [r][3].Variable L_MESSAGE |  |
| [r][4].Field {3} | [r][4].Variable T_TRAIN |  |
| [r][5].Field {4} | [r][5].Variable NID_ENGINE |  |
| [r][6].Field {5} | [r][6].Variable NID_TEXTMESSAGE | [r][6].Remarks Identity of the text message that the driver has acknowledg ed. |
| [r][7].Field {6} | [r][7].Variable Packet 0 or 1 |  |
- WordTraceId: 25226

###### 8.6.16[2].[t]*.[r][2]
- WordTraceId: 25074

###### 8.6.16[2].[t]*.[r][2].Field
{1}
- PlainText: 1
- WordTraceId: 25074

###### 8.6.16[2].[t]*.[r][2].Variable
NID_MESSAGE
- WordTraceId: 25075

###### 8.6.16[2].[t]*.[r][3]
- WordTraceId: 25089

###### 8.6.16[2].[t]*.[r][3].Field
{2}
- PlainText: 2
- WordTraceId: 25089

###### 8.6.16[2].[t]*.[r][3].Variable
L_MESSAGE
- WordTraceId: 25090

###### 8.6.16[2].[t]*.[r][4]
- WordTraceId: 25102

###### 8.6.16[2].[t]*.[r][4].Field
{3}
- PlainText: 3
- WordTraceId: 25102

###### 8.6.16[2].[t]*.[r][4].Variable
T_TRAIN
- WordTraceId: 25103

###### 8.6.16[2].[t]*.[r][5]
- WordTraceId: 25113

###### 8.6.16[2].[t]*.[r][5].Field
{4}
- PlainText: 4
- WordTraceId: 25113

###### 8.6.16[2].[t]*.[r][5].Variable
NID_ENGINE
- WordTraceId: 25114

###### 8.6.16[2].[t]*.[r][6]
- WordTraceId: 25127

###### 8.6.16[2].[t]*.[r][6].Field
{5}
- PlainText: 5
- WordTraceId: 25127

###### 8.6.16[2].[t]*.[r][6].Variable
NID_TEXTMESSAGE
- WordTraceId: 25128

###### 8.6.16[2].[t]*.[r][6].Remarks
Identity of the text message that the driver has acknowledg ed.
- PlainText: Identity of the text message that the driver has acknowledged.
- WordTraceId: 25144

###### 8.6.16[2].[t]*.[r][7]
- WordTraceId: 25208

###### 8.6.16[2].[t]*.[r][7].Field
{6}
- PlainText: 6
- WordTraceId: 25208

###### 8.6.16[2].[t]*.[r][7].Variable
Packet 0 or 1
- WordTraceId: 25209

##### 8.6.17
Message 159: Session established
- WordTraceId: 25227

##### 8.6.17[2]
- WordTraceId: 25261

###### 8.6.17[2].[t]*
| Field No. | VARIABLE/ PACKET | Remarks |
| --- | --- | --- |
| [r][2].Field {1} | [r][2].Variable NID_MESSAGE |  |
| [r][3].Field {2} | [r][3].Variable L_MESSAGE |  |
| [r][4].Field {3} | [r][4].Variable T_TRAIN |  |
| [r][5].Field {4} | [r][5].Variable NID_ENGINE |  |
| [r][6].Field {5} | [r][6].Variable Optional Packet |  |
- WordTraceId: 25370

###### 8.6.17[2].[t]*.[r][2]
- WordTraceId: 25297

###### 8.6.17[2].[t]*.[r][2].Field
{1}
- PlainText: 1
- WordTraceId: 25297

###### 8.6.17[2].[t]*.[r][2].Variable
NID_MESSAGE
- WordTraceId: 25298

###### 8.6.17[2].[t]*.[r][3]
- WordTraceId: 25312

###### 8.6.17[2].[t]*.[r][3].Field
{2}
- PlainText: 2
- WordTraceId: 25312

###### 8.6.17[2].[t]*.[r][3].Variable
L_MESSAGE
- WordTraceId: 25313

###### 8.6.17[2].[t]*.[r][4]
- WordTraceId: 25325

###### 8.6.17[2].[t]*.[r][4].Field
{3}
- PlainText: 3
- WordTraceId: 25325

###### 8.6.17[2].[t]*.[r][4].Variable
T_TRAIN
- WordTraceId: 25326

###### 8.6.17[2].[t]*.[r][5]
- WordTraceId: 25336

###### 8.6.17[2].[t]*.[r][5].Field
{4}
- PlainText: 4
- WordTraceId: 25336

###### 8.6.17[2].[t]*.[r][5].Variable
NID_ENGINE
- WordTraceId: 25337

###### 8.6.17[2].[t]*.[r][6]
- WordTraceId: 25350

###### 8.6.17[2].[t]*.[r][6].Field
{5}
- PlainText: 5
- WordTraceId: 25350

###### 8.6.17[2].[t]*.[r][6].Variable
Optional Packet
- WordTraceId: 25351

#### 8.7
Definition of Radio Messages from Track to Train
- WordTraceId: 25370

##### 8.7.1
Message 2: SR Authorisation
- WordTraceId: 25419

##### 8.7.1[2]
- WordTraceId: 25448

###### 8.7.1[2].[t]*
| Field No. | VARIABLE | Remarks |
| --- | --- | --- |
| [r][2].Field {1} | [r][2].Variable NID_MESSAGE |  |
| [r][3].Field {2} | [r][3].Variable L_MESSAGE |  |
| [r][4].Field {3} | [r][4].Variable T_TRAIN |  |
| [r][5].Field {4} | [r][5].Variable M_ACK |  |
| [r][6].Field {5} | [r][6].Variable NID_LRBG |  |
| [r][7].Field {6} | [r][7].Variable Q_SCALE |  |
| [r][8].Field {7} | [r][8].Variable D_SR |  |
| [r][9].Field {8} | [r][9].Variable Optional packets |  |
- WordTraceId: 25576

###### 8.7.1[2].[t]*.[r][2]
- WordTraceId: 25476

###### 8.7.1[2].[t]*.[r][2].Field
{1}
- PlainText: 1
- WordTraceId: 25476

###### 8.7.1[2].[t]*.[r][2].Variable
NID_MESSAGE
- WordTraceId: 25477

###### 8.7.1[2].[t]*.[r][3]
- WordTraceId: 25491

###### 8.7.1[2].[t]*.[r][3].Field
{2}
- PlainText: 2
- WordTraceId: 25491

###### 8.7.1[2].[t]*.[r][3].Variable
L_MESSAGE
- WordTraceId: 25492

###### 8.7.1[2].[t]*.[r][4]
- WordTraceId: 25504

###### 8.7.1[2].[t]*.[r][4].Field
{3}
- PlainText: 3
- WordTraceId: 25504

###### 8.7.1[2].[t]*.[r][4].Variable
T_TRAIN
- WordTraceId: 25505

###### 8.7.1[2].[t]*.[r][5]
- WordTraceId: 25515

###### 8.7.1[2].[t]*.[r][5].Field
{4}
- PlainText: 4
- WordTraceId: 25515

###### 8.7.1[2].[t]*.[r][5].Variable
M_ACK
- WordTraceId: 25516

###### 8.7.1[2].[t]*.[r][6]
- WordTraceId: 25524

###### 8.7.1[2].[t]*.[r][6].Field
{5}
- PlainText: 5
- WordTraceId: 25524

###### 8.7.1[2].[t]*.[r][6].Variable
NID_LRBG
- WordTraceId: 25525

###### 8.7.1[2].[t]*.[r][7]
- WordTraceId: 25536

###### 8.7.1[2].[t]*.[r][7].Field
{6}
- PlainText: 6
- WordTraceId: 25536

###### 8.7.1[2].[t]*.[r][7].Variable
Q_SCALE
- WordTraceId: 25537

###### 8.7.1[2].[t]*.[r][8]
- WordTraceId: 25547

###### 8.7.1[2].[t]*.[r][8].Field
{7}
- PlainText: 7
- WordTraceId: 25547

###### 8.7.1[2].[t]*.[r][8].Variable
D_SR
- WordTraceId: 25548

###### 8.7.1[2].[t]*.[r][9]
- WordTraceId: 25555

###### 8.7.1[2].[t]*.[r][9].Field
{8}
- PlainText: 8
- WordTraceId: 25555

###### 8.7.1[2].[t]*.[r][9].Variable
Optional packets
- WordTraceId: 25556

##### 8.7.2
Message 3: Movement Authority
- WordTraceId: 25576

##### 8.7.2[2]
- WordTraceId: 25607

###### 8.7.2[2].[t]*
| Field No. | VARIABLE | Remarks |
| --- | --- | --- |
| [r][2].Field {1} | [r][2].Variable NID_MESSAGE |  |
| [r][3].Field {2} | [r][3].Variable L_MESSAGE |  |
| [r][4].Field {3} | [r][4].Variable T_TRAIN |  |
| [r][5].Field {4} | [r][5].Variable M_ACK |  |
| [r][6].Field {5} | [r][6].Variable NID_LRBG |  |
| [r][7].Field {6} | [r][7].Variable Level 2/3 Movement Authority | [r][7].Remarks Packet 15 |
| [r][8].Field {7} | [r][8].Variable Optional packets |  |
- WordTraceId: 25757

###### 8.7.2[2].[t]*.[r][2]
- WordTraceId: 25635

###### 8.7.2[2].[t]*.[r][2].Field
{1}
- PlainText: 1
- WordTraceId: 25635

###### 8.7.2[2].[t]*.[r][2].Variable
NID_MESSAGE
- WordTraceId: 25636

###### 8.7.2[2].[t]*.[r][3]
- WordTraceId: 25650

###### 8.7.2[2].[t]*.[r][3].Field
{2}
- PlainText: 2
- WordTraceId: 25650

###### 8.7.2[2].[t]*.[r][3].Variable
L_MESSAGE
- WordTraceId: 25651

###### 8.7.2[2].[t]*.[r][4]
- WordTraceId: 25663

###### 8.7.2[2].[t]*.[r][4].Field
{3}
- PlainText: 3
- WordTraceId: 25663

###### 8.7.2[2].[t]*.[r][4].Variable
T_TRAIN
- WordTraceId: 25664

###### 8.7.2[2].[t]*.[r][5]
- WordTraceId: 25674

###### 8.7.2[2].[t]*.[r][5].Field
{4}
- PlainText: 4
- WordTraceId: 25674

###### 8.7.2[2].[t]*.[r][5].Variable
M_ACK
- WordTraceId: 25675

###### 8.7.2[2].[t]*.[r][6]
- WordTraceId: 25683

###### 8.7.2[2].[t]*.[r][6].Field
{5}
- PlainText: 5
- WordTraceId: 25683

###### 8.7.2[2].[t]*.[r][6].Variable
NID_LRBG
- WordTraceId: 25684

###### 8.7.2[2].[t]*.[r][7]
- WordTraceId: 25695

###### 8.7.2[2].[t]*.[r][7].Field
{6}
- PlainText: 6
- WordTraceId: 25695

###### 8.7.2[2].[t]*.[r][7].Variable
Level 2/3 Movement Authority
- WordTraceId: 25696

###### 8.7.2[2].[t]*.[r][7].Remarks
Packet 15
- WordTraceId: 25725

###### 8.7.2[2].[t]*.[r][8]
- WordTraceId: 25736

###### 8.7.2[2].[t]*.[r][8].Field
{7}
- PlainText: 7
- WordTraceId: 25736

###### 8.7.2[2].[t]*.[r][8].Variable
Optional packets
- WordTraceId: 25737

##### 8.7.3
Message 6: Recognition of exit from TRIP mode
- WordTraceId: 25758

##### 8.7.3[2]
- WordTraceId: 25805

###### 8.7.3[2].[t]*
| Field No. | VARIABLE | Remarks |
| --- | --- | --- |
| [r][2].Field {1} | [r][2].Variable NID_MESSAGE |  |
| [r][3].Field {2} | [r][3].Variable L_MESSAGE |  |
| [r][4].Field {3} | [r][4].Variable T_TRAIN |  |
| [r][5].Field {4} | [r][5].Variable M_ACK |  |
| [r][6].Field {5} | [r][6].Variable NID_LRBG |  |
- WordTraceId: 25894

###### 8.7.3[2].[t]*.[r][2]
- WordTraceId: 25833

###### 8.7.3[2].[t]*.[r][2].Field
{1}
- PlainText: 1
- WordTraceId: 25833

###### 8.7.3[2].[t]*.[r][2].Variable
NID_MESSAGE
- WordTraceId: 25834

###### 8.7.3[2].[t]*.[r][3]
- WordTraceId: 25848

###### 8.7.3[2].[t]*.[r][3].Field
{2}
- PlainText: 2
- WordTraceId: 25848

###### 8.7.3[2].[t]*.[r][3].Variable
L_MESSAGE
- WordTraceId: 25849

###### 8.7.3[2].[t]*.[r][4]
- WordTraceId: 25861

###### 8.7.3[2].[t]*.[r][4].Field
{3}
- PlainText: 3
- WordTraceId: 25861

###### 8.7.3[2].[t]*.[r][4].Variable
T_TRAIN
- WordTraceId: 25862

###### 8.7.3[2].[t]*.[r][5]
- WordTraceId: 25872

###### 8.7.3[2].[t]*.[r][5].Field
{4}
- PlainText: 4
- WordTraceId: 25872

###### 8.7.3[2].[t]*.[r][5].Variable
M_ACK
- WordTraceId: 25873

###### 8.7.3[2].[t]*.[r][6]
- WordTraceId: 25881

###### 8.7.3[2].[t]*.[r][6].Field
{5}
- PlainText: 5
- WordTraceId: 25881

###### 8.7.3[2].[t]*.[r][6].Variable
NID_LRBG
- WordTraceId: 25882

##### 8.7.4
Message 8: Acknowledgement of Train Data
- WordTraceId: 25894

##### 8.7.4[2]
- WordTraceId: 25936

###### 8.7.4[2].[t]*
| Field No. | VARIABLE | Remarks |
| --- | --- | --- |
| [r][2].Field {1} | [r][2].Variable NID_MESSAGE |  |
| [r][3].Field {2} | [r][3].Variable L_MESSAGE |  |
| [r][4].Field {3} | [r][4].Variable T_TRAIN |  |
| [r][5].Field {4} | [r][5].Variable M_ACK |  |
| [r][6].Field {5} | [r][6].Variable NID_LRBG |  |
| [r][7].Field {6} | [r][7].Variable T_TRAIN | [r][7].Remarks Reference to received train data message |
- WordTraceId: 26076

###### 8.7.4[2].[t]*.[r][2]
- WordTraceId: 25964

###### 8.7.4[2].[t]*.[r][2].Field
{1}
- PlainText: 1
- WordTraceId: 25964

###### 8.7.4[2].[t]*.[r][2].Variable
NID_MESSAGE
- WordTraceId: 25965

###### 8.7.4[2].[t]*.[r][3]
- WordTraceId: 25979

###### 8.7.4[2].[t]*.[r][3].Field
{2}
- PlainText: 2
- WordTraceId: 25979

###### 8.7.4[2].[t]*.[r][3].Variable
L_MESSAGE
- WordTraceId: 25980

###### 8.7.4[2].[t]*.[r][4]
- WordTraceId: 25992

###### 8.7.4[2].[t]*.[r][4].Field
{3}
- PlainText: 3
- WordTraceId: 25992

###### 8.7.4[2].[t]*.[r][4].Variable
T_TRAIN
- WordTraceId: 25993

###### 8.7.4[2].[t]*.[r][5]
- WordTraceId: 26003

###### 8.7.4[2].[t]*.[r][5].Field
{4}
- PlainText: 4
- WordTraceId: 26003

###### 8.7.4[2].[t]*.[r][5].Variable
M_ACK
- WordTraceId: 26004

###### 8.7.4[2].[t]*.[r][6]
- WordTraceId: 26012

###### 8.7.4[2].[t]*.[r][6].Field
{5}
- PlainText: 5
- WordTraceId: 26012

###### 8.7.4[2].[t]*.[r][6].Variable
NID_LRBG
- WordTraceId: 26013

###### 8.7.4[2].[t]*.[r][7]
- WordTraceId: 26024

###### 8.7.4[2].[t]*.[r][7].Field
{6}
- PlainText: 6
- WordTraceId: 26024

###### 8.7.4[2].[t]*.[r][7].Variable
T_TRAIN
- WordTraceId: 26025

###### 8.7.4[2].[t]*.[r][7].Remarks
Reference to received train data message
- WordTraceId: 26033

##### 8.7.5
Message 9: Request to Shorten MA
- WordTraceId: 26076

##### 8.7.5[2]
- WordTraceId: 26110

###### 8.7.5[2].[t]*
| Field No. | VARIABLE | Remarks |
| --- | --- | --- |
| [r][2].Field {1} | [r][2].Variable NID_MESSAGE |  |
| [r][3].Field {2} | [r][3].Variable L_MESSAGE |  |
| [r][4].Field {3} | [r][4].Variable T_TRAIN |  |
| [r][5].Field {4} | [r][5].Variable M_ACK |  |
| [r][6].Field {5} | [r][6].Variable NID_LRBG |  |
| [r][7].Field {6} | [r][7].Variable Level 2/3 Movement Authority | [r][7].Remarks Packet 15 |
| [r][8].Field {7} | [r][8].Variable Optional packet | [r][8].Remarks Packet 80 |
- WordTraceId: 26268

###### 8.7.5[2].[t]*.[r][2]
- WordTraceId: 26138

###### 8.7.5[2].[t]*.[r][2].Field
{1}
- PlainText: 1
- WordTraceId: 26138

###### 8.7.5[2].[t]*.[r][2].Variable
NID_MESSAGE
- WordTraceId: 26139

###### 8.7.5[2].[t]*.[r][3]
- WordTraceId: 26153

###### 8.7.5[2].[t]*.[r][3].Field
{2}
- PlainText: 2
- WordTraceId: 26153

###### 8.7.5[2].[t]*.[r][3].Variable
L_MESSAGE
- WordTraceId: 26154

###### 8.7.5[2].[t]*.[r][4]
- WordTraceId: 26166

###### 8.7.5[2].[t]*.[r][4].Field
{3}
- PlainText: 3
- WordTraceId: 26166

###### 8.7.5[2].[t]*.[r][4].Variable
T_TRAIN
- WordTraceId: 26167

###### 8.7.5[2].[t]*.[r][5]
- WordTraceId: 26177

###### 8.7.5[2].[t]*.[r][5].Field
{4}
- PlainText: 4
- WordTraceId: 26177

###### 8.7.5[2].[t]*.[r][5].Variable
M_ACK
- WordTraceId: 26178

###### 8.7.5[2].[t]*.[r][6]
- WordTraceId: 26186

###### 8.7.5[2].[t]*.[r][6].Field
{5}
- PlainText: 5
- WordTraceId: 26186

###### 8.7.5[2].[t]*.[r][6].Variable
NID_LRBG
- WordTraceId: 26187

###### 8.7.5[2].[t]*.[r][7]
- WordTraceId: 26198

###### 8.7.5[2].[t]*.[r][7].Field
{6}
- PlainText: 6
- WordTraceId: 26198

###### 8.7.5[2].[t]*.[r][7].Variable
Level 2/3 Movement Authority
- WordTraceId: 26199

###### 8.7.5[2].[t]*.[r][7].Remarks
Packet 15
- WordTraceId: 26228

###### 8.7.5[2].[t]*.[r][8]
- WordTraceId: 26239

###### 8.7.5[2].[t]*.[r][8].Field
{7}
- PlainText: 7
- WordTraceId: 26239

###### 8.7.5[2].[t]*.[r][8].Variable
Optional packet
- WordTraceId: 26240

###### 8.7.5[2].[t]*.[r][8].Remarks
Packet 80
- WordTraceId: 26256

##### 8.7.6
Message 15: Conditional Emergency Stop
- WordTraceId: 26268

##### 8.7.6[2]
- WordTraceId: 26308

###### 8.7.6[2].[t]*
| Field No. | VARIABLE | Remarks |
| --- | --- | --- |
| [r][2].Field {1} | [r][2].Variable NID_MESSAGE |  |
| [r][3].Field {2} | [r][3].Variable L_MESSAGE |  |
| [r][4].Field {3} | [r][4].Variable T_TRAIN |  |
| [r][5].Field {4} | [r][5].Variable M_ACK |  |
| [r][6].Field {5} | [r][6].Variable NID_LRBG |  |
| [r][7].Field {6} | [r][7].Variable NID_EM | [r][7].Remarks Identification Number of the Emergency Stop Message. |
| [r][8].Field {7} | [r][8].Variable Q_SCALE |  |
| [r][9].Field {8} | [r][9].Variable D_REF |  |
| [r][10].Field {9} | [r][10].Variable Q_DIR |  |
| [r][11].Field {10} | [r][11].Variable D_EMERGENCYSTOP | [r][11].Remarks Distance between LRBG and the position reference to the emergency stop. |
- WordTraceId: 26578

###### 8.7.6[2].[t]*.[r][2]
- WordTraceId: 26336

###### 8.7.6[2].[t]*.[r][2].Field
{1}
- PlainText: 1
- WordTraceId: 26336

###### 8.7.6[2].[t]*.[r][2].Variable
NID_MESSAGE
- WordTraceId: 26337

###### 8.7.6[2].[t]*.[r][3]
- WordTraceId: 26351

###### 8.7.6[2].[t]*.[r][3].Field
{2}
- PlainText: 2
- WordTraceId: 26351

###### 8.7.6[2].[t]*.[r][3].Variable
L_MESSAGE
- WordTraceId: 26352

###### 8.7.6[2].[t]*.[r][4]
- WordTraceId: 26364

###### 8.7.6[2].[t]*.[r][4].Field
{3}
- PlainText: 3
- WordTraceId: 26364

###### 8.7.6[2].[t]*.[r][4].Variable
T_TRAIN
- WordTraceId: 26365

###### 8.7.6[2].[t]*.[r][5]
- WordTraceId: 26375

###### 8.7.6[2].[t]*.[r][5].Field
{4}
- PlainText: 4
- WordTraceId: 26375

###### 8.7.6[2].[t]*.[r][5].Variable
M_ACK
- WordTraceId: 26376

###### 8.7.6[2].[t]*.[r][6]
- WordTraceId: 26384

###### 8.7.6[2].[t]*.[r][6].Field
{5}
- PlainText: 5
- WordTraceId: 26384

###### 8.7.6[2].[t]*.[r][6].Variable
NID_LRBG
- WordTraceId: 26385

###### 8.7.6[2].[t]*.[r][7]
- WordTraceId: 26396

###### 8.7.6[2].[t]*.[r][7].Field
{6}
- PlainText: 6
- WordTraceId: 26396

###### 8.7.6[2].[t]*.[r][7].Variable
NID_EM
- WordTraceId: 26397

###### 8.7.6[2].[t]*.[r][7].Remarks
Identification Number of the Emergency Stop Message.
- WordTraceId: 26404

###### 8.7.6[2].[t]*.[r][8]
- WordTraceId: 26458

###### 8.7.6[2].[t]*.[r][8].Field
{7}
- PlainText: 7
- WordTraceId: 26458

###### 8.7.6[2].[t]*.[r][8].Variable
Q_SCALE
- WordTraceId: 26459

###### 8.7.6[2].[t]*.[r][9]
- WordTraceId: 26469

###### 8.7.6[2].[t]*.[r][9].Field
{8}
- PlainText: 8
- WordTraceId: 26469

###### 8.7.6[2].[t]*.[r][9].Variable
D_REF
- WordTraceId: 26470

###### 8.7.6[2].[t]*.[r][10]
- WordTraceId: 26478

###### 8.7.6[2].[t]*.[r][10].Field
{9}
- PlainText: 9
- WordTraceId: 26478

###### 8.7.6[2].[t]*.[r][10].Variable
Q_DIR
- WordTraceId: 26479

###### 8.7.6[2].[t]*.[r][11]
- WordTraceId: 26487

###### 8.7.6[2].[t]*.[r][11].Field
{10}
- PlainText: 10
- WordTraceId: 26487

###### 8.7.6[2].[t]*.[r][11].Variable
D_EMERGENCYSTOP
- WordTraceId: 26488

###### 8.7.6[2].[t]*.[r][11].Remarks
Distance between LRBG and the position reference to the emergency stop.
- WordTraceId: 26504

##### 8.7.7
Message 16: Unconditional Emergency Stop
- WordTraceId: 26579

##### 8.7.7[2]
- WordTraceId: 26621

###### 8.7.7[2].[t]*
| Field No. | VARIABLE | Remarks |
| --- | --- | --- |
| [r][2].Field {1} | [r][2].Variable NID_MESSAGE |  |
| [r][3].Field {2} | [r][3].Variable L_MESSAGE |  |
| [r][4].Field {3} | [r][4].Variable T_TRAIN |  |
| [r][5].Field {4} | [r][5].Variable M_ACK |  |
| [r][6].Field {5} | [r][6].Variable NID_LRBG |  |
| [r][7].Field {6} | [r][7].Variable NID_EM | [r][7].Remarks Identification Number of the Emergency Stop Message. |
- WordTraceId: 26772

###### 8.7.7[2].[t]*.[r][2]
- WordTraceId: 26649

###### 8.7.7[2].[t]*.[r][2].Field
{1}
- PlainText: 1
- WordTraceId: 26649

###### 8.7.7[2].[t]*.[r][2].Variable
NID_MESSAGE
- WordTraceId: 26650

###### 8.7.7[2].[t]*.[r][3]
- WordTraceId: 26664

###### 8.7.7[2].[t]*.[r][3].Field
{2}
- PlainText: 2
- WordTraceId: 26664

###### 8.7.7[2].[t]*.[r][3].Variable
L_MESSAGE
- WordTraceId: 26665

###### 8.7.7[2].[t]*.[r][4]
- WordTraceId: 26677

###### 8.7.7[2].[t]*.[r][4].Field
{3}
- PlainText: 3
- WordTraceId: 26677

###### 8.7.7[2].[t]*.[r][4].Variable
T_TRAIN
- WordTraceId: 26678

###### 8.7.7[2].[t]*.[r][5]
- WordTraceId: 26688

###### 8.7.7[2].[t]*.[r][5].Field
{4}
- PlainText: 4
- WordTraceId: 26688

###### 8.7.7[2].[t]*.[r][5].Variable
M_ACK
- WordTraceId: 26689

###### 8.7.7[2].[t]*.[r][6]
- WordTraceId: 26697

###### 8.7.7[2].[t]*.[r][6].Field
{5}
- PlainText: 5
- WordTraceId: 26697

###### 8.7.7[2].[t]*.[r][6].Variable
NID_LRBG
- WordTraceId: 26698

###### 8.7.7[2].[t]*.[r][7]
- WordTraceId: 26709

###### 8.7.7[2].[t]*.[r][7].Field
{6}
- PlainText: 6
- WordTraceId: 26709

###### 8.7.7[2].[t]*.[r][7].Variable
NID_EM
- WordTraceId: 26710

###### 8.7.7[2].[t]*.[r][7].Remarks
Identification Number of the Emergency Stop Message.
- WordTraceId: 26717

##### 8.7.8
Message 18: Revocation of Emergency Stop
- WordTraceId: 26772

##### 8.7.8[2]
- WordTraceId: 26814

###### 8.7.8[2].[t]*
| Field No. | VARIABLE | Remarks |
| --- | --- | --- |
| [r][2].Field {1} | [r][2].Variable NID_MESSAGE |  |
| [r][3].Field {2} | [r][3].Variable L_MESSAGE |  |
| [r][4].Field {3} | [r][4].Variable T_TRAIN |  |
| [r][5].Field {4} | [r][5].Variable M_ACK |  |
| [r][6].Field {5} | [r][6].Variable NID_LRBG |  |
| [r][7].Field {6} | [r][7].Variable NID_EM | [r][7].Remarks Identification Number of the Emergency Stop Message. |
- WordTraceId: 26965

###### 8.7.8[2].[t]*.[r][2]
- WordTraceId: 26842

###### 8.7.8[2].[t]*.[r][2].Field
{1}
- PlainText: 1
- WordTraceId: 26842

###### 8.7.8[2].[t]*.[r][2].Variable
NID_MESSAGE
- WordTraceId: 26843

###### 8.7.8[2].[t]*.[r][3]
- WordTraceId: 26857

###### 8.7.8[2].[t]*.[r][3].Field
{2}
- PlainText: 2
- WordTraceId: 26857

###### 8.7.8[2].[t]*.[r][3].Variable
L_MESSAGE
- WordTraceId: 26858

###### 8.7.8[2].[t]*.[r][4]
- WordTraceId: 26870

###### 8.7.8[2].[t]*.[r][4].Field
{3}
- PlainText: 3
- WordTraceId: 26870

###### 8.7.8[2].[t]*.[r][4].Variable
T_TRAIN
- WordTraceId: 26871

###### 8.7.8[2].[t]*.[r][5]
- WordTraceId: 26881

###### 8.7.8[2].[t]*.[r][5].Field
{4}
- PlainText: 4
- WordTraceId: 26881

###### 8.7.8[2].[t]*.[r][5].Variable
M_ACK
- WordTraceId: 26882

###### 8.7.8[2].[t]*.[r][6]
- WordTraceId: 26890

###### 8.7.8[2].[t]*.[r][6].Field
{5}
- PlainText: 5
- WordTraceId: 26890

###### 8.7.8[2].[t]*.[r][6].Variable
NID_LRBG
- WordTraceId: 26891

###### 8.7.8[2].[t]*.[r][7]
- WordTraceId: 26902

###### 8.7.8[2].[t]*.[r][7].Field
{6}
- PlainText: 6
- WordTraceId: 26902

###### 8.7.8[2].[t]*.[r][7].Variable
NID_EM
- WordTraceId: 26903

###### 8.7.8[2].[t]*.[r][7].Remarks
Identification Number of the Emergency Stop Message.
- WordTraceId: 26910

##### 8.7.9
Message 24: General message
- WordTraceId: 26965

##### 8.7.9[2]
- WordTraceId: 26994

###### 8.7.9[2].[t]*
| Field No. | VARIABLE | Remarks |
| --- | --- | --- |
| [r][2].Field {1} | [r][2].Variable NID_MESSAGE |  |
| [r][3].Field {2} | [r][3].Variable L_MESSAGE |  |
| [r][4].Field {3} | [r][4].Variable T_TRAIN |  |
| [r][5].Field {4} | [r][5].Variable M_ACK |  |
| [r][6].Field {5} | [r][6].Variable NID_LRBG |  |
| [r][7].Field {6} | [r][7].Variable Optional packets |  |
- WordTraceId: 27103

###### 8.7.9[2].[t]*.[r][2]
- WordTraceId: 27022

###### 8.7.9[2].[t]*.[r][2].Field
{1}
- PlainText: 1
- WordTraceId: 27022

###### 8.7.9[2].[t]*.[r][2].Variable
NID_MESSAGE
- WordTraceId: 27023

###### 8.7.9[2].[t]*.[r][3]
- WordTraceId: 27037

###### 8.7.9[2].[t]*.[r][3].Field
{2}
- PlainText: 2
- WordTraceId: 27037

###### 8.7.9[2].[t]*.[r][3].Variable
L_MESSAGE
- WordTraceId: 27038

###### 8.7.9[2].[t]*.[r][4]
- WordTraceId: 27050

###### 8.7.9[2].[t]*.[r][4].Field
{3}
- PlainText: 3
- WordTraceId: 27050

###### 8.7.9[2].[t]*.[r][4].Variable
T_TRAIN
- WordTraceId: 27051

###### 8.7.9[2].[t]*.[r][5]
- WordTraceId: 27061

###### 8.7.9[2].[t]*.[r][5].Field
{4}
- PlainText: 4
- WordTraceId: 27061

###### 8.7.9[2].[t]*.[r][5].Variable
M_ACK
- WordTraceId: 27062

###### 8.7.9[2].[t]*.[r][6]
- WordTraceId: 27070

###### 8.7.9[2].[t]*.[r][6].Field
{5}
- PlainText: 5
- WordTraceId: 27070

###### 8.7.9[2].[t]*.[r][6].Variable
NID_LRBG
- WordTraceId: 27071

###### 8.7.9[2].[t]*.[r][7]
- WordTraceId: 27082

###### 8.7.9[2].[t]*.[r][7].Field
{6}
- PlainText: 6
- WordTraceId: 27082

###### 8.7.9[2].[t]*.[r][7].Variable
Optional packets
- WordTraceId: 27083

##### 8.7.10
Message 27: SH Refused
- WordTraceId: 27104

##### 8.7.10[2]
- WordTraceId: 27128

###### 8.7.10[2].[t]*
| Field No. | VARIABLE | Remarks |
| --- | --- | --- |
| [r][2].Field {1} | [r][2].Variable NID_MESSAGE |  |
| [r][3].Field {2} | [r][3].Variable L_MESSAGE |  |
| [r][4].Field {3} | [r][4].Variable T_TRAIN |  |
| [r][5].Field {4} | [r][5].Variable M_ACK |  |
| [r][6].Field {5} | [r][6].Variable NID_LRBG |  |
| [r][7].Field {6} | [r][7].Variable T_TRAIN | [r][7].Remarks Time stamp of the shunting request. |
- WordTraceId: 27263

###### 8.7.10[2].[t]*.[r][2]
- WordTraceId: 27156

###### 8.7.10[2].[t]*.[r][2].Field
{1}
- PlainText: 1
- WordTraceId: 27156

###### 8.7.10[2].[t]*.[r][2].Variable
NID_MESSAGE
- WordTraceId: 27157

###### 8.7.10[2].[t]*.[r][3]
- WordTraceId: 27171

###### 8.7.10[2].[t]*.[r][3].Field
{2}
- PlainText: 2
- WordTraceId: 27171

###### 8.7.10[2].[t]*.[r][3].Variable
L_MESSAGE
- WordTraceId: 27172

###### 8.7.10[2].[t]*.[r][4]
- WordTraceId: 27184

###### 8.7.10[2].[t]*.[r][4].Field
{3}
- PlainText: 3
- WordTraceId: 27184

###### 8.7.10[2].[t]*.[r][4].Variable
T_TRAIN
- WordTraceId: 27185

###### 8.7.10[2].[t]*.[r][5]
- WordTraceId: 27195

###### 8.7.10[2].[t]*.[r][5].Field
{4}
- PlainText: 4
- WordTraceId: 27195

###### 8.7.10[2].[t]*.[r][5].Variable
M_ACK
- WordTraceId: 27196

###### 8.7.10[2].[t]*.[r][6]
- WordTraceId: 27204

###### 8.7.10[2].[t]*.[r][6].Field
{5}
- PlainText: 5
- WordTraceId: 27204

###### 8.7.10[2].[t]*.[r][6].Variable
NID_LRBG
- WordTraceId: 27205

###### 8.7.10[2].[t]*.[r][7]
- WordTraceId: 27216

###### 8.7.10[2].[t]*.[r][7].Field
{6}
- PlainText: 6
- WordTraceId: 27216

###### 8.7.10[2].[t]*.[r][7].Variable
T_TRAIN
- WordTraceId: 27217

###### 8.7.10[2].[t]*.[r][7].Remarks
Time stamp of the shunting request.
- WordTraceId: 27225

##### 8.7.11
Message 28: SH Authorised
- WordTraceId: 27263

##### 8.7.11[2]
- WordTraceId: 27290

###### 8.7.11[2].[t]*
| Field No. | VARIABLE | Remarks |
| --- | --- | --- |
| [r][2].Field {1} | [r][2].Variable NID_MESSAGE |  |
| [r][3].Field {2} | [r][3].Variable L_MESSAGE |  |
| [r][4].Field {3} | [r][4].Variable T_TRAIN |  |
| [r][5].Field {4} | [r][5].Variable M_ACK |  |
| [r][6].Field {5} | [r][6].Variable NID_LRBG |  |
| [r][7].Field {6} | [r][7].Variable T_TRAIN | [r][7].Remarks Time stamp of the shunting request. |
| [r][8].Field {7} | [r][8].Variable Optional packets |  |
- WordTraceId: 27445

###### 8.7.11[2].[t]*.[r][2]
- WordTraceId: 27318

###### 8.7.11[2].[t]*.[r][2].Field
{1}
- PlainText: 1
- WordTraceId: 27318

###### 8.7.11[2].[t]*.[r][2].Variable
NID_MESSAGE
- WordTraceId: 27319

###### 8.7.11[2].[t]*.[r][3]
- WordTraceId: 27333

###### 8.7.11[2].[t]*.[r][3].Field
{2}
- PlainText: 2
- WordTraceId: 27333

###### 8.7.11[2].[t]*.[r][3].Variable
L_MESSAGE
- WordTraceId: 27334

###### 8.7.11[2].[t]*.[r][4]
- WordTraceId: 27346

###### 8.7.11[2].[t]*.[r][4].Field
{3}
- PlainText: 3
- WordTraceId: 27346

###### 8.7.11[2].[t]*.[r][4].Variable
T_TRAIN
- WordTraceId: 27347

###### 8.7.11[2].[t]*.[r][5]
- WordTraceId: 27357

###### 8.7.11[2].[t]*.[r][5].Field
{4}
- PlainText: 4
- WordTraceId: 27357

###### 8.7.11[2].[t]*.[r][5].Variable
M_ACK
- WordTraceId: 27358

###### 8.7.11[2].[t]*.[r][6]
- WordTraceId: 27366

###### 8.7.11[2].[t]*.[r][6].Field
{5}
- PlainText: 5
- WordTraceId: 27366

###### 8.7.11[2].[t]*.[r][6].Variable
NID_LRBG
- WordTraceId: 27367

###### 8.7.11[2].[t]*.[r][7]
- WordTraceId: 27378

###### 8.7.11[2].[t]*.[r][7].Field
{6}
- PlainText: 6
- WordTraceId: 27378

###### 8.7.11[2].[t]*.[r][7].Variable
T_TRAIN
- WordTraceId: 27379

###### 8.7.11[2].[t]*.[r][7].Remarks
Time stamp of the shunting request.
- WordTraceId: 27387

###### 8.7.11[2].[t]*.[r][8]
- WordTraceId: 27424

###### 8.7.11[2].[t]*.[r][8].Field
{7}
- PlainText: 7
- WordTraceId: 27424

###### 8.7.11[2].[t]*.[r][8].Variable
Optional packets
- WordTraceId: 27425

##### 8.7.12
Message 32: RBC/RIU System Version
- WordTraceId: 27445

##### 8.7.12[2]
- WordTraceId: 27481

###### 8.7.12[2].[t]*
| Field No. | VARIABLE | Remarks |
| --- | --- | --- |
| [r][2].Field {1} | [r][2].Variable NID_MESSAGE |  |
| [r][3].Field {2} | [r][3].Variable L_MESSAGE |  |
| [r][4].Field {3} | [r][4].Variable T_TRAIN |  |
| [r][5].Field {4} | [r][5].Variable M_ACK |  |
| [r][6].Field {5} | [r][6].Variable NID_LRBG |  |
| [r][7].Field {6} | [r][7].Variable M_VERSION | [r][7].Remarks Version of the ERTMS/ETCS system . |
- WordTraceId: 27616

###### 8.7.12[2].[t]*.[r][2]
- WordTraceId: 27509

###### 8.7.12[2].[t]*.[r][2].Field
{1}
- PlainText: 1
- WordTraceId: 27509

###### 8.7.12[2].[t]*.[r][2].Variable
NID_MESSAGE
- WordTraceId: 27510

###### 8.7.12[2].[t]*.[r][3]
- WordTraceId: 27524

###### 8.7.12[2].[t]*.[r][3].Field
{2}
- PlainText: 2
- WordTraceId: 27524

###### 8.7.12[2].[t]*.[r][3].Variable
L_MESSAGE
- WordTraceId: 27525

###### 8.7.12[2].[t]*.[r][4]
- WordTraceId: 27537

###### 8.7.12[2].[t]*.[r][4].Field
{3}
- PlainText: 3
- WordTraceId: 27537

###### 8.7.12[2].[t]*.[r][4].Variable
T_TRAIN
- WordTraceId: 27538

###### 8.7.12[2].[t]*.[r][5]
- WordTraceId: 27548

###### 8.7.12[2].[t]*.[r][5].Field
{4}
- PlainText: 4
- WordTraceId: 27548

###### 8.7.12[2].[t]*.[r][5].Variable
M_ACK
- WordTraceId: 27549

###### 8.7.12[2].[t]*.[r][6]
- WordTraceId: 27557

###### 8.7.12[2].[t]*.[r][6].Field
{5}
- PlainText: 5
- WordTraceId: 27557

###### 8.7.12[2].[t]*.[r][6].Variable
NID_LRBG
- WordTraceId: 27558

###### 8.7.12[2].[t]*.[r][7]
- WordTraceId: 27569

###### 8.7.12[2].[t]*.[r][7].Field
{6}
- PlainText: 6
- WordTraceId: 27569

###### 8.7.12[2].[t]*.[r][7].Variable
M_VERSION
- WordTraceId: 27570

###### 8.7.12[2].[t]*.[r][7].Remarks
Version of the ERTMS/ETCS system .
- PlainText: Version of the ERTMS/ETCS system.
- WordTraceId: 27580

##### 8.7.13
Message 33: MA with Shifted Location Reference
- WordTraceId: 27616

##### 8.7.13[2]
- WordTraceId: 27664

###### 8.7.13[2].[t]*
| Field No. | VARIABLE | Remarks |
| --- | --- | --- |
| [r][2].Field {1} | [r][2].Variable NID_MESSAGE |  |
| [r][3].Field {2} | [r][3].Variable L_MESSAGE |  |
| [r][4].Field {3} | [r][4].Variable T_TRAIN |  |
| [r][5].Field {4} | [r][5].Variable M_ACK |  |
| [r][6].Field {5} | [r][6].Variable NID_LRBG |  |
| [r][7].Field {6} | [r][7].Variable Q_SCALE |  |
| [r][8].Field {7} | [r][8].Variable D_REF | [r][8].Remarks Reference Distance |
| [r][9].Field {8} | [r][9].Variable Level 2/3 Movement Authority | [r][9].Remarks Packet 15 |
| [r][10].Field {9} | [r][10].Variable Optional packets |  |
- WordTraceId: 27852

###### 8.7.13[2].[t]*.[r][2]
- WordTraceId: 27692

###### 8.7.13[2].[t]*.[r][2].Field
{1}
- PlainText: 1
- WordTraceId: 27692

###### 8.7.13[2].[t]*.[r][2].Variable
NID_MESSAGE
- WordTraceId: 27693

###### 8.7.13[2].[t]*.[r][3]
- WordTraceId: 27707

###### 8.7.13[2].[t]*.[r][3].Field
{2}
- PlainText: 2
- WordTraceId: 27707

###### 8.7.13[2].[t]*.[r][3].Variable
L_MESSAGE
- WordTraceId: 27708

###### 8.7.13[2].[t]*.[r][4]
- WordTraceId: 27720

###### 8.7.13[2].[t]*.[r][4].Field
{3}
- PlainText: 3
- WordTraceId: 27720

###### 8.7.13[2].[t]*.[r][4].Variable
T_TRAIN
- WordTraceId: 27721

###### 8.7.13[2].[t]*.[r][5]
- WordTraceId: 27731

###### 8.7.13[2].[t]*.[r][5].Field
{4}
- PlainText: 4
- WordTraceId: 27731

###### 8.7.13[2].[t]*.[r][5].Variable
M_ACK
- WordTraceId: 27732

###### 8.7.13[2].[t]*.[r][6]
- WordTraceId: 27740

###### 8.7.13[2].[t]*.[r][6].Field
{5}
- PlainText: 5
- WordTraceId: 27740

###### 8.7.13[2].[t]*.[r][6].Variable
NID_LRBG
- WordTraceId: 27741

###### 8.7.13[2].[t]*.[r][7]
- WordTraceId: 27752

###### 8.7.13[2].[t]*.[r][7].Field
{6}
- PlainText: 6
- WordTraceId: 27752

###### 8.7.13[2].[t]*.[r][7].Variable
Q_SCALE
- WordTraceId: 27753

###### 8.7.13[2].[t]*.[r][8]
- WordTraceId: 27763

###### 8.7.13[2].[t]*.[r][8].Field
{7}
- PlainText: 7
- WordTraceId: 27763

###### 8.7.13[2].[t]*.[r][8].Variable
D_REF
- WordTraceId: 27764

###### 8.7.13[2].[t]*.[r][8].Remarks
Reference Distance
- WordTraceId: 27770

###### 8.7.13[2].[t]*.[r][9]
- WordTraceId: 27790

###### 8.7.13[2].[t]*.[r][9].Field
{8}
- PlainText: 8
- WordTraceId: 27790

###### 8.7.13[2].[t]*.[r][9].Variable
Level 2/3 Movement Authority
- WordTraceId: 27791

###### 8.7.13[2].[t]*.[r][9].Remarks
Packet 15
- WordTraceId: 27820

###### 8.7.13[2].[t]*.[r][10]
- WordTraceId: 27831

###### 8.7.13[2].[t]*.[r][10].Field
{9}
- PlainText: 9
- WordTraceId: 27831

###### 8.7.13[2].[t]*.[r][10].Variable
Optional packets
- WordTraceId: 27832

##### 8.7.14
Message 34: Track Ahead Free Request
- WordTraceId: 27853

##### 8.7.14[2]
- WordTraceId: 27891

###### 8.7.14[2].[t]*
| Field No. | VARIABLE | Remarks |
| --- | --- | --- |
| [r][2].Field {1} | [r][2].Variable NID_MESSAGE |  |
| [r][3].Field {2} | [r][3].Variable L_MESSAGE |  |
| [r][4].Field {3} | [r][4].Variable T_TRAIN |  |
| [r][5].Field {4} | [r][5].Variable M_ACK |  |
| [r][6].Field {5} | [r][6].Variable NID_LRBG |  |
| [r][7].Field {6} | [r][7].Variable Q_SCALE |  |
| [r][8].Field {7} | [r][8].Variable D_REF |  |
| [r][9].Field {8} | [r][9].Variable Q_DIR |  |
| [r][10].Field {9} | [r][10].Variable D_TAFDISPLAY |  |
| [r][11].Field {10} | [r][11].Variable L_TAFDISPLAY |  |
- WordTraceId: 28041

###### 8.7.14[2].[t]*.[r][2]
- WordTraceId: 27919

###### 8.7.14[2].[t]*.[r][2].Field
{1}
- PlainText: 1
- WordTraceId: 27919

###### 8.7.14[2].[t]*.[r][2].Variable
NID_MESSAGE
- WordTraceId: 27920

###### 8.7.14[2].[t]*.[r][3]
- WordTraceId: 27934

###### 8.7.14[2].[t]*.[r][3].Field
{2}
- PlainText: 2
- WordTraceId: 27934

###### 8.7.14[2].[t]*.[r][3].Variable
L_MESSAGE
- WordTraceId: 27935

###### 8.7.14[2].[t]*.[r][4]
- WordTraceId: 27947

###### 8.7.14[2].[t]*.[r][4].Field
{3}
- PlainText: 3
- WordTraceId: 27947

###### 8.7.14[2].[t]*.[r][4].Variable
T_TRAIN
- WordTraceId: 27948

###### 8.7.14[2].[t]*.[r][5]
- WordTraceId: 27958

###### 8.7.14[2].[t]*.[r][5].Field
{4}
- PlainText: 4
- WordTraceId: 27958

###### 8.7.14[2].[t]*.[r][5].Variable
M_ACK
- WordTraceId: 27959

###### 8.7.14[2].[t]*.[r][6]
- WordTraceId: 27967

###### 8.7.14[2].[t]*.[r][6].Field
{5}
- PlainText: 5
- WordTraceId: 27967

###### 8.7.14[2].[t]*.[r][6].Variable
NID_LRBG
- WordTraceId: 27968

###### 8.7.14[2].[t]*.[r][7]
- WordTraceId: 27979

###### 8.7.14[2].[t]*.[r][7].Field
{6}
- PlainText: 6
- WordTraceId: 27979

###### 8.7.14[2].[t]*.[r][7].Variable
Q_SCALE
- WordTraceId: 27980

###### 8.7.14[2].[t]*.[r][8]
- WordTraceId: 27990

###### 8.7.14[2].[t]*.[r][8].Field
{7}
- PlainText: 7
- WordTraceId: 27990

###### 8.7.14[2].[t]*.[r][8].Variable
D_REF
- WordTraceId: 27991

###### 8.7.14[2].[t]*.[r][9]
- WordTraceId: 27999

###### 8.7.14[2].[t]*.[r][9].Field
{8}
- PlainText: 8
- WordTraceId: 27999

###### 8.7.14[2].[t]*.[r][9].Variable
Q_DIR
- WordTraceId: 28000

###### 8.7.14[2].[t]*.[r][10]
- WordTraceId: 28008

###### 8.7.14[2].[t]*.[r][10].Field
{9}
- PlainText: 9
- WordTraceId: 28008

###### 8.7.14[2].[t]*.[r][10].Variable
D_TAFDISPLAY
- WordTraceId: 28009

###### 8.7.14[2].[t]*.[r][11]
- WordTraceId: 28024

###### 8.7.14[2].[t]*.[r][11].Field
{10}
- PlainText: 10
- WordTraceId: 28024

###### 8.7.14[2].[t]*.[r][11].Variable
L_TAFDISPLAY
- WordTraceId: 28025

##### 8.7.15
Message 37: Infill MA
- WordTraceId: 28041

##### 8.7.15[2]
- WordTraceId: 28064

###### 8.7.15[2].[t]*
| Field No. | VARIABLE | Remarks |
| --- | --- | --- |
| [r][2].Field {1} | [r][2].Variable NID_MESSAGE |  |
| [r][3].Field {2} | [r][3].Variable L_MESSAGE |  |
| [r][4].Field {3} | [r][4].Variable T_TRAIN |  |
| [r][5].Field {4} | [r][5].Variable M_ACK |  |
| [r][6].Field {5} | [r][6].Variable NID_LRBG |  |
| [r][7].Field {6} | [r][7].Variable Infill Location Reference | [r][7].Remarks Packet 136 |
| [r][8].Field {7} | [r][8].Variable Level 1 Movement Authority | [r][8].Remarks Packet 12 |
| [r][9].Field {8} | [r][9].Variable Optional packets |  |
- WordTraceId: 28251

###### 8.7.15[2].[t]*.[r][2]
- WordTraceId: 28092

###### 8.7.15[2].[t]*.[r][2].Field
{1}
- PlainText: 1
- WordTraceId: 28092

###### 8.7.15[2].[t]*.[r][2].Variable
NID_MESSAGE
- WordTraceId: 28093

###### 8.7.15[2].[t]*.[r][3]
- WordTraceId: 28107

###### 8.7.15[2].[t]*.[r][3].Field
{2}
- PlainText: 2
- WordTraceId: 28107

###### 8.7.15[2].[t]*.[r][3].Variable
L_MESSAGE
- WordTraceId: 28108

###### 8.7.15[2].[t]*.[r][4]
- WordTraceId: 28120

###### 8.7.15[2].[t]*.[r][4].Field
{3}
- PlainText: 3
- WordTraceId: 28120

###### 8.7.15[2].[t]*.[r][4].Variable
T_TRAIN
- WordTraceId: 28121

###### 8.7.15[2].[t]*.[r][5]
- WordTraceId: 28131

###### 8.7.15[2].[t]*.[r][5].Field
{4}
- PlainText: 4
- WordTraceId: 28131

###### 8.7.15[2].[t]*.[r][5].Variable
M_ACK
- WordTraceId: 28132

###### 8.7.15[2].[t]*.[r][6]
- WordTraceId: 28140

###### 8.7.15[2].[t]*.[r][6].Field
{5}
- PlainText: 5
- WordTraceId: 28140

###### 8.7.15[2].[t]*.[r][6].Variable
NID_LRBG
- WordTraceId: 28141

###### 8.7.15[2].[t]*.[r][7]
- WordTraceId: 28152

###### 8.7.15[2].[t]*.[r][7].Field
{6}
- PlainText: 6
- WordTraceId: 28152

###### 8.7.15[2].[t]*.[r][7].Variable
Infill Location Reference
- WordTraceId: 28153

###### 8.7.15[2].[t]*.[r][7].Remarks
Packet 136
- WordTraceId: 28179

###### 8.7.15[2].[t]*.[r][8]
- WordTraceId: 28191

###### 8.7.15[2].[t]*.[r][8].Field
{7}
- PlainText: 7
- WordTraceId: 28191

###### 8.7.15[2].[t]*.[r][8].Variable
Level 1 Movement Authority
- WordTraceId: 28192

###### 8.7.15[2].[t]*.[r][8].Remarks
Packet 12
- WordTraceId: 28219

###### 8.7.15[2].[t]*.[r][9]
- WordTraceId: 28230

###### 8.7.15[2].[t]*.[r][9].Field
{8}
- PlainText: 8
- WordTraceId: 28230

###### 8.7.15[2].[t]*.[r][9].Variable
Optional packets
- WordTraceId: 28231

##### 8.7.16
Message 38: Initiation of a communication session
- WordTraceId: 28251

##### 8.7.16[2]
- WordTraceId: 28302

###### 8.7.16[2].[t]*
| Field No. | VARIABLE | Remarks |
| --- | --- | --- |
|  | [r][2].Variable |  |
| [r][3].Field {1} | [r][3].Variable NID_MESSAGE |  |
| [r][4].Field {2} | [r][4].Variable L_MESSAGE |  |
| [r][5].Field {3} | [r][5].Variable T_TRAIN | [r][5].Remarks always set to unknown |
| [r][6].Field {4} | [r][6].Variable M_ACK |  |
| [r][7].Field {5} | [r][7].Variable NID_LRBG | [r][7].Remarks always set to unknown |
- WordTraceId: 28437

###### 8.7.16[2].[t]*.[r][2]
- WordTraceId: 28330

###### 8.7.16[2].[t]*.[r][2].Variable
- WordTraceId: 28331

###### 8.7.16[2].[t]*.[r][3]
- WordTraceId: 28334

###### 8.7.16[2].[t]*.[r][3].Field
{1}
- PlainText: 1
- WordTraceId: 28334

###### 8.7.16[2].[t]*.[r][3].Variable
NID_MESSAGE
- WordTraceId: 28335

###### 8.7.16[2].[t]*.[r][4]
- WordTraceId: 28349

###### 8.7.16[2].[t]*.[r][4].Field
{2}
- PlainText: 2
- WordTraceId: 28349

###### 8.7.16[2].[t]*.[r][4].Variable
L_MESSAGE
- WordTraceId: 28350

###### 8.7.16[2].[t]*.[r][5]
- WordTraceId: 28362

###### 8.7.16[2].[t]*.[r][5].Field
{3}
- PlainText: 3
- WordTraceId: 28362

###### 8.7.16[2].[t]*.[r][5].Variable
T_TRAIN
- WordTraceId: 28363

###### 8.7.16[2].[t]*.[r][5].Remarks
always set to unknown
- WordTraceId: 28371

###### 8.7.16[2].[t]*.[r][6]
- WordTraceId: 28394

###### 8.7.16[2].[t]*.[r][6].Field
{4}
- PlainText: 4
- WordTraceId: 28394

###### 8.7.16[2].[t]*.[r][6].Variable
M_ACK
- WordTraceId: 28395

###### 8.7.16[2].[t]*.[r][7]
- WordTraceId: 28403

###### 8.7.16[2].[t]*.[r][7].Field
{5}
- PlainText: 5
- WordTraceId: 28403

###### 8.7.16[2].[t]*.[r][7].Variable
NID_LRBG
- WordTraceId: 28404

###### 8.7.16[2].[t]*.[r][7].Remarks
always set to unknown
- WordTraceId: 28413

##### 8.7.17
Message 39: Acknowledgement of termination of a communication session
- WordTraceId: 28437

##### 8.7.17[2]
- WordTraceId: 28508

###### 8.7.17[2].[t]*
| Field No. | VARIABLE | Remarks |
| --- | --- | --- |
| [r][2].Field {1} | [r][2].Variable NID_MESSAGE |  |
| [r][3].Field {2} | [r][3].Variable L_MESSAGE |  |
| [r][4].Field {3} | [r][4].Variable T_TRAIN |  |
| [r][5].Field {4} | [r][5].Variable M_ACK | [r][5].Remarks a lways set to 0 |
| [r][6].Field {5} | [r][6].Variable NID_LRBG |  |
- WordTraceId: 28612

###### 8.7.17[2].[t]*.[r][2]
- WordTraceId: 28536

###### 8.7.17[2].[t]*.[r][2].Field
{1}
- PlainText: 1
- WordTraceId: 28536

###### 8.7.17[2].[t]*.[r][2].Variable
NID_MESSAGE
- WordTraceId: 28537

###### 8.7.17[2].[t]*.[r][3]
- WordTraceId: 28551

###### 8.7.17[2].[t]*.[r][3].Field
{2}
- PlainText: 2
- WordTraceId: 28551

###### 8.7.17[2].[t]*.[r][3].Variable
L_MESSAGE
- WordTraceId: 28552

###### 8.7.17[2].[t]*.[r][4]
- WordTraceId: 28564

###### 8.7.17[2].[t]*.[r][4].Field
{3}
- PlainText: 3
- WordTraceId: 28564

###### 8.7.17[2].[t]*.[r][4].Variable
T_TRAIN
- WordTraceId: 28565

###### 8.7.17[2].[t]*.[r][5]
- WordTraceId: 28575

###### 8.7.17[2].[t]*.[r][5].Field
{4}
- PlainText: 4
- WordTraceId: 28575

###### 8.7.17[2].[t]*.[r][5].Variable
M_ACK
- WordTraceId: 28576

###### 8.7.17[2].[t]*.[r][5].Remarks
a lways set to 0
- PlainText: always set to 0
- WordTraceId: 28582

###### 8.7.17[2].[t]*.[r][6]
- WordTraceId: 28599

###### 8.7.17[2].[t]*.[r][6].Field
{5}
- PlainText: 5
- WordTraceId: 28599

###### 8.7.17[2].[t]*.[r][6].Variable
NID_LRBG
- WordTraceId: 28600

##### 8.7.18
Message 40: Train Rejected
- WordTraceId: 28612

##### 8.7.18[2]
- WordTraceId: 28640

###### 8.7.18[2].[t]*
| Field No. | VARIABLE | Remarks |
| --- | --- | --- |
| [r][2].Field {1} | [r][2].Variable NID_MESSAGE |  |
| [r][3].Field {2} | [r][3].Variable L_MESSAGE |  |
| [r][4].Field {3} | [r][4].Variable T_TRAIN |  |
| [r][5].Field {4} | [r][5].Variable M_ACK |  |
| [r][6].Field {5} | [r][6].Variable NID_LRBG |  |
- WordTraceId: 28729

###### 8.7.18[2].[t]*.[r][2]
- WordTraceId: 28668

###### 8.7.18[2].[t]*.[r][2].Field
{1}
- PlainText: 1
- WordTraceId: 28668

###### 8.7.18[2].[t]*.[r][2].Variable
NID_MESSAGE
- WordTraceId: 28669

###### 8.7.18[2].[t]*.[r][3]
- WordTraceId: 28683

###### 8.7.18[2].[t]*.[r][3].Field
{2}
- PlainText: 2
- WordTraceId: 28683

###### 8.7.18[2].[t]*.[r][3].Variable
L_MESSAGE
- WordTraceId: 28684

###### 8.7.18[2].[t]*.[r][4]
- WordTraceId: 28696

###### 8.7.18[2].[t]*.[r][4].Field
{3}
- PlainText: 3
- WordTraceId: 28696

###### 8.7.18[2].[t]*.[r][4].Variable
T_TRAIN
- WordTraceId: 28697

###### 8.7.18[2].[t]*.[r][5]
- WordTraceId: 28707

###### 8.7.18[2].[t]*.[r][5].Field
{4}
- PlainText: 4
- WordTraceId: 28707

###### 8.7.18[2].[t]*.[r][5].Variable
M_ACK
- WordTraceId: 28708

###### 8.7.18[2].[t]*.[r][6]
- WordTraceId: 28716

###### 8.7.18[2].[t]*.[r][6].Field
{5}
- PlainText: 5
- WordTraceId: 28716

###### 8.7.18[2].[t]*.[r][6].Variable
NID_LRBG
- WordTraceId: 28717

##### 8.7.19
Message 41: Train Accepted
- WordTraceId: 28730

##### 8.7.19[2]
- WordTraceId: 28758

###### 8.7.19[2].[t]*
| Field No. | VARIABLE | Remarks |
| --- | --- | --- |
| [r][2].Field {1} | [r][2].Variable NID_MESSAGE |  |
| [r][3].Field {2} | [r][3].Variable L_MESSAGE |  |
| [r][4].Field {3} | [r][4].Variable T_TRAIN |  |
| [r][5].Field {4} | [r][5].Variable M_ACK |  |
| [r][6].Field {5} | [r][6].Variable NID_LRBG |  |
- WordTraceId: 28847

###### 8.7.19[2].[t]*.[r][2]
- WordTraceId: 28786

###### 8.7.19[2].[t]*.[r][2].Field
{1}
- PlainText: 1
- WordTraceId: 28786

###### 8.7.19[2].[t]*.[r][2].Variable
NID_MESSAGE
- WordTraceId: 28787

###### 8.7.19[2].[t]*.[r][3]
- WordTraceId: 28801

###### 8.7.19[2].[t]*.[r][3].Field
{2}
- PlainText: 2
- WordTraceId: 28801

###### 8.7.19[2].[t]*.[r][3].Variable
L_MESSAGE
- WordTraceId: 28802

###### 8.7.19[2].[t]*.[r][4]
- WordTraceId: 28814

###### 8.7.19[2].[t]*.[r][4].Field
{3}
- PlainText: 3
- WordTraceId: 28814

###### 8.7.19[2].[t]*.[r][4].Variable
T_TRAIN
- WordTraceId: 28815

###### 8.7.19[2].[t]*.[r][5]
- WordTraceId: 28825

###### 8.7.19[2].[t]*.[r][5].Field
{4}
- PlainText: 4
- WordTraceId: 28825

###### 8.7.19[2].[t]*.[r][5].Variable
M_ACK
- WordTraceId: 28826

###### 8.7.19[2].[t]*.[r][6]
- WordTraceId: 28834

###### 8.7.19[2].[t]*.[r][6].Field
{5}
- PlainText: 5
- WordTraceId: 28834

###### 8.7.19[2].[t]*.[r][6].Variable
NID_LRBG
- WordTraceId: 28835

##### 8.7.20
Intentionally deleted
- WordTraceId: 28847

##### 8.7.21
Message 43: SoM position report confirmed by RBC
- WordTraceId: 28869

##### 8.7.21[2]
- WordTraceId: 28919

###### 8.7.21[2].[t]*
| Field No. | VARIABLE | Remarks |
| --- | --- | --- |
| [r][2].Field {1} | [r][2].Variable NID_MESSAGE |  |
| [r][3].Field {2} | [r][3].Variable L_MESSAGE |  |
| [r][4].Field {3} | [r][4].Variable T_TRAIN |  |
| [r][5].Field {4} | [r][5].Variable M_ACK |  |
| [r][6].Field {5} | [r][6].Variable NID_LRBG |  |
- WordTraceId: 29008

###### 8.7.21[2].[t]*.[r][2]
- WordTraceId: 28947

###### 8.7.21[2].[t]*.[r][2].Field
{1}
- PlainText: 1
- WordTraceId: 28947

###### 8.7.21[2].[t]*.[r][2].Variable
NID_MESSAGE
- WordTraceId: 28948

###### 8.7.21[2].[t]*.[r][3]
- WordTraceId: 28962

###### 8.7.21[2].[t]*.[r][3].Field
{2}
- PlainText: 2
- WordTraceId: 28962

###### 8.7.21[2].[t]*.[r][3].Variable
L_MESSAGE
- WordTraceId: 28963

###### 8.7.21[2].[t]*.[r][4]
- WordTraceId: 28975

###### 8.7.21[2].[t]*.[r][4].Field
{3}
- PlainText: 3
- WordTraceId: 28975

###### 8.7.21[2].[t]*.[r][4].Variable
T_TRAIN
- WordTraceId: 28976

###### 8.7.21[2].[t]*.[r][5]
- WordTraceId: 28986

###### 8.7.21[2].[t]*.[r][5].Field
{4}
- PlainText: 4
- WordTraceId: 28986

###### 8.7.21[2].[t]*.[r][5].Variable
M_ACK
- WordTraceId: 28987

###### 8.7.21[2].[t]*.[r][6]
- WordTraceId: 28995

###### 8.7.21[2].[t]*.[r][6].Field
{5}
- PlainText: 5
- WordTraceId: 28995

###### 8.7.21[2].[t]*.[r][6].Variable
NID_LRBG
- WordTraceId: 28996

##### 8.7.22
Message 45: Assignment of coordinate system
- WordTraceId: 29008

##### 8.7.22[2]
- WordTraceId: 29053

###### 8.7.22[2].[t]*
| Field No. | VARIABLE | Remarks |
| --- | --- | --- |
| [r][2].Field {1} | [r][2].Variable NID_MESSAGE |  |
| [r][3].Field {2} | [r][3].Variable L_MESSAGE |  |
| [r][4].Field {3} | [r][4].Variable T_TRAIN |  |
| [r][5].Field {4} | [r][5].Variable M_ACK |  |
| [r][6].Field {5} | [r][6].Variable NID_LRBG |  |
| [r][7].Field {6} | [r][7].Variable Q_ ORIENTATION |  |
- WordTraceId: 29159

###### 8.7.22[2].[t]*.[r][2]
- WordTraceId: 29081

###### 8.7.22[2].[t]*.[r][2].Field
{1}
- PlainText: 1
- WordTraceId: 29081

###### 8.7.22[2].[t]*.[r][2].Variable
NID_MESSAGE
- WordTraceId: 29082

###### 8.7.22[2].[t]*.[r][3]
- WordTraceId: 29096

###### 8.7.22[2].[t]*.[r][3].Field
{2}
- PlainText: 2
- WordTraceId: 29096

###### 8.7.22[2].[t]*.[r][3].Variable
L_MESSAGE
- WordTraceId: 29097

###### 8.7.22[2].[t]*.[r][4]
- WordTraceId: 29109

###### 8.7.22[2].[t]*.[r][4].Field
{3}
- PlainText: 3
- WordTraceId: 29109

###### 8.7.22[2].[t]*.[r][4].Variable
T_TRAIN
- WordTraceId: 29110

###### 8.7.22[2].[t]*.[r][5]
- WordTraceId: 29120

###### 8.7.22[2].[t]*.[r][5].Field
{4}
- PlainText: 4
- WordTraceId: 29120

###### 8.7.22[2].[t]*.[r][5].Variable
M_ACK
- WordTraceId: 29121

###### 8.7.22[2].[t]*.[r][6]
- WordTraceId: 29129

###### 8.7.22[2].[t]*.[r][6].Field
{5}
- PlainText: 5
- WordTraceId: 29129

###### 8.7.22[2].[t]*.[r][6].Variable
NID_LRBG
- WordTraceId: 29130

###### 8.7.22[2].[t]*.[r][7]
- WordTraceId: 29141

###### 8.7.22[2].[t]*.[r][7].Field
{6}
- PlainText: 6
- WordTraceId: 29141

###### 8.7.22[2].[t]*.[r][7].Variable
Q_ ORIENTATION
- PlainText: Q_ORIENTATION
- WordTraceId: 29142
